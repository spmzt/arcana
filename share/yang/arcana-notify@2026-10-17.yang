module arcana-notify {
  yang-version 1.1;
  namespace "urn:arcana:yang:arcana-notify";
  prefix arcntf;

  import ietf-netconf-acm {
    prefix nacm;
    reference
      "RFC 8341: Network Configuration Access Control Model";
  }

  organization
    "Arcana";
  contact
    "Pouria Mousavizadeh Tehrani <pouria@FreeBSD.org>";
  description
    "A message sent to a Telegram chat by a bot, from a host that
     reaches the world outside: the console's alerts and a workflow's
     notify step.  The Bot API's sendMessage, POSTed over HTTPS by the
     base system's fetch(3), which checks api.telegram.org's
     certificate against the host's CAs.  The bot's token is used for
     the request and forgotten: it is in no trace nor log.  The notify
     operation of arcana.yaml converted (Y-3).";

  revision 2026-10-17 {
    description
      "Initial revision.";
  }

  rpc notify {
    nacm:default-deny-all;
    description
      "Send a message to a Telegram chat.";
    input {
      leaf token {
        type string {
          length "1..128";
        }
        mandatory true;
        description
          "The bot's token, as BotFather gives it: digits, a colon,
           letters, digits, _ and -.  Used for this message and
           forgotten.  Its form is the agent's to check, which says
           what is wrong and never the token, where a pattern's
           refusal would show it.";
      }
      leaf chat {
        type string {
          length "1..33";
        }
        mandatory true;
        description
          "The chat: its number (negative for a group), or @ and a
           channel's name of 5 to 32 letters, digits and _; the
           agent checks it.";
      }
      leaf text {
        type string {
          length "1..4096";
        }
        mandatory true;
        description
          "The message.";
      }
    }
  }
}
