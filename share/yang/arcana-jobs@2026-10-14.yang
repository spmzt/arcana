module arcana-jobs {
  yang-version 1.1;
  namespace "urn:arcana:yang:arcana-jobs";
  prefix arcjob;

  import ietf-netconf-acm {
    prefix nacm;
    reference
      "RFC 8341: Network Configuration Access Control Model";
  }

  import cblink-gen {
    prefix cg;
  }

  include arcana-jobs-kinds {
    revision-date 2026-10-14;
  }

  organization
    "Arcana";
  contact
    "Pouria Mousavizadeh Tehrani <pouria@FreeBSD.org>";
  description
    "The agent's jobs: the changes it is given, queued and run one
     after another in the order given, whether or not the client stays,
     their outcomes kept; each with its trace, the steps it took, a
     flat list each naming its parent, read by the job's read action (a
     read of every job would carry every trace).  A change a safe-mode
     job made waits, unconfirmed, for confirm, and is undone without it
     in time.  How many jobs of pkg in jails run at once, lanes, is the
     configuration, kept in jobs.conf beside the agent's other kept
     files.

     The kinds of change are arcana-jobs-kinds's, made from
     share/arcana/jobs.yaml.";

  revision 2026-10-14 {
    description
      "Initial revision.";
  }

  typedef job-state {
    type enumeration {
      enum queued {
        value 0;
        description
          "Waiting its turn.";
      }
      enum running {
        value 1;
        description
          "Being done.";
      }
      enum done {
        value 2;
        description
          "Finished; ok says how.";
      }
      enum cancelled {
        value 3;
        description
          "Taken out of the queue before it ran.";
      }
      enum unconfirmed {
        value 4;
        description
          "The change is made and waits for confirm; without it in
           time, it is undone.";
      }
    }
    description
      "Where a job is.";
  }

  grouping job-info {
    description
      "What a job is and where it is.";
    leaf kind {
      type job-kind;
      description
        "Its kind.";
    }
    leaf title {
      type string;
      description
        "What it does, in words.";
    }
    leaf state {
      type job-state;
      description
        "Where it is.";
    }
    leaf ok {
      type boolean;
      description
        "Done: whether it succeeded.";
    }
    leaf error {
      type string;
      description
        "Done and failed: why.";
    }
    leaf created {
      type int64;
      units "seconds";
      description
        "When it was queued, in seconds since the Epoch.";
    }
    leaf started {
      type int64;
      units "seconds";
      description
        "When it began.";
    }
    leaf finished {
      type int64;
      units "seconds";
      description
        "When it ended.";
    }
    leaf peer {
      type string;
      description
        "Who gave it.";
    }
    leaf confirm-by {
      type int64;
      units "seconds";
      description
        "Unconfirmed: when it is undone without confirm.";
    }
    leaf user {
      type string;
      description
        "Who asked for it: the user of the request that queued it,
         RFC 8341's, the console's user it acted for or the console
         itself; absent for the recovery session, which peer names.";
    }
  }

  grouping step {
    description
      "A step of a trace: what the agent did for a request or a job.";
    leaf id {
      type uint32;
      description
        "Its number in the trace.";
    }
    leaf parent {
      type int32 {
        range "-1..max";
      }
      description
        "The step it is part of; -1, the root.";
    }
    leaf kind {
      type enumeration {
        enum daemon {
          value 0;
        }
        enum lib {
          value 1;
        }
        enum syscall {
          value 2;
        }
        enum file {
          value 3;
        }
        enum exec {
          value 4;
        }
      }
      description
        "What it was: the agent's own, a library's call, a system
         call, a file read or written, a program run.";
    }
    leaf label {
      type string;
      description
        "What it was, named.";
    }
    leaf detail {
      type string;
      description
        "What it was, said.";
    }
    leaf status {
      type enumeration {
        enum ok {
          value 0;
        }
        enum failed {
          value 1;
        }
        enum incomplete {
          value 2;
        }
      }
      description
        "How it went.";
    }
    leaf duration {
      type uint64;
      units "microseconds";
      description
        "How long it took.";
    }
    leaf-list argv {
      type string;
      ordered-by user;
      description
        "A program run: its arguments.";
    }
    leaf exit {
      type int32;
      description
        "A program run: its exit status.";
    }
    leaf output {
      type binary;
      description
        "A program run: what it wrote to its standard output.";
    }
    leaf error-output {
      type binary;
      description
        "And to its standard error.";
    }
  }

  container jobs {
    description
      "The queued, running and recent jobs, and how many jobs of pkg in
       jails run at once.";
    leaf lanes {
      type uint8 {
        range "1..32";
      }
      default "4";
      description
        "How many jobs of pkg in jails run at once; a lane at work
         finishes its job.";
    }
    leaf activity {
      type string;
      config false;
      description
        "What the agent does now that is not a job: a request a client
         waits for, which holds up changes as a job does.";
    }
    leaf since {
      type int64;
      units "seconds";
      config false;
      description
        "When it began, in seconds since the Epoch.";
    }
    leaf stopping {
      type boolean;
      config false;
      description
        "Whether the agent is stopping: no job is taken.";
    }
    list job {
      key "id";
      config false;
      description
        "A job, without its trace.";
      leaf id {
        type uint64;
        description
          "Its number, the agent's.";
      }
      uses job-info;
      action cancel {
        nacm:default-deny-all;
        description
          "A job not yet started taken out of the queue.";
        output {
          leaf state {
            type job-state;
            description
              "Where it is now.";
          }
        }
      }
      action confirm {
        nacm:default-deny-all;
        description
          "An unconfirmed job's change kept: that the request arrived
           is the point, the client still reaches the host.";
        output {
          leaf state {
            type job-state;
            description
              "Where it is now.";
          }
        }
      }
      action read {
        description
          "The job with its trace so far: the steps it took, in the
           order taken, each naming its parent, the tree in a flat
           list.";
        output {
          uses job-info;
          list step {
            cg:struct "step";
            key "id";
            description
              "A step of its trace, in the order taken; each names its
               parent, the tree in a flat list.";
            uses step;
          }
        }
      }
    }
  }

  grouping submitted-change {
    description
      "A change as it is given: what it is, and whether it is safe.";
    uses change;
    leaf safe {
      type boolean;
      description
        "Undo the change unless confirm comes in time: the client
         that still reaches the host after it confirms, one it cut
         off cannot, and the host comes back by itself.  A kind,
         or a verb of one, that cannot be undone refuses it, saying
         why.";
    }
    leaf safe-wait {
      type uint32 {
        range "10..max";
      }
      units "seconds";
      description
        "With safe: how long the change waits to be confirmed
         before it is undone, in place of the agent's own (-w).";
    }
  }

  rpc submit {
    nacm:default-deny-all;
    description
      "Changes queued, to run in the order given.";
    input {
      list change {
        cg:struct "submit_input_change";
        min-elements 1;
        description
          "A change.";
        uses submitted-change;
      }
    }
    output {
      leaf-list id {
        type uint64;
        description
          "The jobs queued, in the order given.";
      }
    }
  }

  rpc dry-run {
    nacm:default-deny-all;
    description
      "What submit would do with the same changes, or what undoing a
       job waiting to be confirmed would do, said by the agent and
       done by nothing: no job is queued, the job named is neither
       confirmed nor cancelled.  The steps are those a job's trace
       would have, in the order taken; a program that only reads is
       run, so that what follows from it is as a job's, any other is
       a step with its arguments and no exit status; a file written,
       a system call that changes the kernel's state, a signal or
       the agent's own restart is a step saying so.  A kind whose
       work cannot be said without doing it is refused, saying so.
       Its rights are submit's: nacm:default-deny-all.";
    input {
      list change {
        cg:struct "submit_input_change";
        description
          "A change, as submit takes it; none with undo.";
        uses submitted-change;
      }
      leaf undo {
        type uint64;
        description
          "A job waiting to be confirmed: what its undo would do,
           as cancel or its timer would do it now.";
      }
    }
    output {
      list step {
        cg:struct "step";
        key "id";
        description
          "A step it would take, as a job's trace has it; each names
           its parent, the tree in a flat list.";
        uses step;
      }
      leaf-list note {
        type string;
        description
          "What the steps do not say: a safe change's timer, a step
           that would fail, an undo with nothing to put back.";
      }
    }
  }

  notification steps {
    description
      "Steps of a request as the agent takes them, each as it begins
       and again as it ends, told to the peer that made the request
       alone, where it joined group notify: the trace a reply would
       carry, heard while the request runs.  A step comes again with
       the same id when it changes; the last told is what it is.";
    list step {
      cg:struct "step";
      key "id";
      description
        "The steps told, one mostly.";
      uses step;
    }
  }
}
