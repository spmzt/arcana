module arcana {
  yang-version 1.1;
  namespace "urn:arcana:yang:arcana";
  prefix arc;

  import cblink-gen {
    prefix cg;
  }
  import ietf-yang-structure-ext {
    prefix sx;
  }

  organization
    "Arcana";
  contact
    "Pouria Mousavizadeh Tehrani <pouria@FreeBSD.org>";
  description
    "What the programs keep of a host for their own use: a jail, a
     service, a job and the change it makes, and the kinds and limits
     they are named by.  No family speaks it: the interim family it was
     is gone, its operations each a YANG module's now (share/yang).
     
     
     Written by share/arcana/wire.awk from share/arcana/arcana.yaml: the structures the programs keep.  Do not edit.";

  revision 2026-10-22 {
    description
      "From the spec as of this day.";
  }

  // max-steps = 1024
  // max-batch = 64
  // max-json = 4194304
  // max-output = 262144

  grouping set-jail {
    description
      "A jail, as the agent's jail.c reads it; arcana-jails has it now:
       kept a structure for the agent's own use.";
    leaf name {
      type string;
    }
    leaf state {
      type uint8 {
        range "0..3";
      }
      description
        "One of jail-state: 0 running 1 stopped 2 dying 3 absent.";
    }
    leaf jid {
      type uint32;
    }
    leaf configured {
      type boolean;
    }
    leaf scope {
      type string;
      description
        "The configuration file that defines the jail.";
    }
    leaf hostname {
      type string;
    }
    leaf path {
      type string;
    }
    leaf-list ip4 {
      type string;
    }
    leaf-list ip6 {
      type string;
    }
    leaf vnet {
      type boolean;
    }
    leaf osrelease {
      type string;
    }
    leaf persist {
      type boolean;
    }
    leaf securelevel {
      type int32;
    }
    leaf parent {
      type uint32;
    }
    leaf children {
      type uint32;
    }
    leaf nproc {
      type uint32;
    }
    leaf rss-kb {
      type uint64;
    }
    leaf cpu-pct {
      type decimal64 {
        fraction-digits 2;
      }
    }
    leaf interface {
      type string;
    }
    list params {
      cg:struct "param";
      description
        "Configured parameters as jail(8) resolves them.";
      uses set-param;
    }
    leaf-list plugins {
      type string;
      description
        "Of a running jail with a network of its own: the plugins it
         has, as a host's, by the programs installed in the jail.";
    }
    leaf-list allow {
      type string;
      description
        "Of a running jail: its allow.* parameters as the kernel has
         them, each \"allow.name=0|1\" (jail-allow sets them).";
    }
    list dying {
      cg:struct "dying-jail";
      description
        "Earlier jails of this name the kernel still has, dying (jls
         -d), while one of the name runs or is defined: a jail removed
         whose sockets or mounts hold it.";
      uses set-dying-jail;
    }
    leaf boot {
      type boolean;
      description
        "Of a jail defined: started at boot by rc.d/jail, jail_enable
         being yes and jail_list empty or naming it.
         ";
    }
  }

  grouping set-dying-jail {
    leaf jid {
      type uint32;
    }
    leaf path {
      type string;
    }
  }

  grouping set-param {
    leaf key {
      type string;
    }
    leaf-list values {
      type string;
    }
  }

  grouping set-service {
    description
      "An rc.d script, as the agent's services.c reads it; arcana-services
       has it now: kept a structure for the agent's own use.";
    leaf name {
      type string;
    }
    leaf path {
      type string;
      description
        "The script, in /etc/rc.d or /usr/local/etc/rc.d.";
    }
    leaf rcvar {
      type string;
      description
        "The rc.conf variable that enables it, if it has one.";
    }
    leaf enabled {
      type boolean;
    }
    leaf running {
      type boolean;
      description
        "What \"service <name> status\" says; absent when not asked.";
    }
    leaf pid {
      type uint32;
    }
    leaf status {
      type string;
      description
        "The status line, as the script printed it.";
    }
  }

  grouping set-variable {
    leaf key {
      type string;
    }
    leaf value {
      type string;
    }
    leaf remove {
      type empty;
      description
        "In a request, unset the variable instead (sysrc -x).";
    }
  }

  grouping set-job-spec {
    description
      "One change to queue; the attributes its kind needs.  arcana-jobs'
       submit carries it now, a change made one by the agent: kept a
       structure for the agent's queue.";
    leaf kind {
      type uint8 {
        range "0..50";
      }
      description
        "One of job-kind: 0 jail-action 1 address 2 service-action 3 service-config 4 pkg-upgrade 5 if-address 6 if-state 7 route 8 if-set 9 if-create 10 if-destroy 11 netgraph 12 wireguard 13 bird 14 if-vnet 15 kmod 16 zfs 17 zpool 18 mount 19 gpart 20 cam 21 sysctl 22 ipfw 23 bridge 24 geneve 25 process 26 pkg-clean 27 ipsec 28 pkg-install 29 ntp 30 rtadvd 31 ipsec-sa 32 jail-conf 33 neighbour 34 cert 35 ssh 36 carp 37 poudriere 38 clamav 39 suricata 40 nfs 41 iscsi 42 hast 43 sysfile 44 geom 45 smtpd 46 jail-allow 47 jail-base 48 reboot 49 speeder 50 monitor.";
    }
    leaf jail {
      type string {
        length "0..255";
      }
    }
    leaf action {
      type uint8 {
        range "0..5";
      }
      description
        "One of action: 0 start 1 stop 2 restart 3 kill 4 enable 5 disable.";
    }
    leaf address {
      type string {
        length "0..64";
      }
    }
    leaf interface {
      type string {
        length "0..15";
      }
    }
    leaf remove {
      type empty;
    }
    leaf live {
      type empty;
    }
    leaf persist {
      type empty;
    }
    leaf service {
      type string {
        length "0..64";
      }
    }
    leaf service-action {
      type uint8 {
        range "0..5";
      }
      description
        "One of service-action: 0 start 1 stop 2 restart 3 reload 4 enable 5 disable.";
    }
    list variables {
      cg:struct "variable";
      uses set-variable;
    }
    leaf-list names {
      type string;
    }
    leaf up {
      type boolean;
      description
        "For if-state.";
    }
    leaf safe {
      type empty;
      description
        "Undo the change unless job-confirm comes for the job within
         the time the daemon allows.  A client that can still reach the
         daemon after the change confirms; one the change cut off
         cannot, and the host comes back by itself.  For the changes
         that can be taken back: if-address, if-state, if-set,
         if-create, route, address, service-config, and a service's
         start, stop, enable and disable.";
    }
    leaf destination {
      type string {
        length "0..64";
      }
      description
        "For route, as default, a network with its prefix length, or a
         host address.";
    }
    leaf gateway {
      type string {
        length "0..512";
      }
      description
        "For route, an address, or the name of an interface; or
         several addresses with a comma between, each with its share
         after an @ when it has one (10.0.0.1@2,10.0.0.2), for a
         route with as many next hops.";
    }
    leaf fib {
      type uint32;
      description
        "For route, the routing table; 0 when not given.  For if-set
         and if-create, the interface's: what is received on it is
         looked up there.";
    }
    leaf mtu {
      type uint32;
      description
        "For if-set and if-create.";
    }
    leaf description {
      type string {
        length "0..64";
      }
      description
        "For if-set and if-create.";
    }
    leaf tunnel-local {
      type string {
        length "0..64";
      }
      description
        "For if-create, a tunnel's outer address on this host.";
    }
    leaf tunnel-remote {
      type string {
        length "0..64";
      }
      description
        "For if-create, a tunnel's outer address at the far end.";
    }
    leaf id {
      type uint32;
      description
        "For if-create, a VLAN tag or a VXLAN identifier.";
    }
    leaf parent {
      type string {
        length "0..15";
      }
      description
        "For if-create, the interface a VLAN rides or a bridge takes in.";
    }
    leaf verb {
      type string {
        length "0..16";
      }
      description
        "For netgraph, wireguard, bird, poudriere, clamav and suricata, what to do.";
    }
    leaf peer {
      type string {
        length "0..44";
      }
      description
        "For wireguard, a peer's public key.";
    }
    leaf endpoint {
      type string {
        length "0..128";
      }
      description
        "For wireguard, where a peer is reached, as address and port.";
    }
    leaf allowed-ips {
      type string {
        length "0..1024";
      }
      description
        "For wireguard, the networks a peer may send from, with commas.";
    }
    leaf keepalive {
      type uint32;
      description
        "For wireguard, seconds between keepalives to a peer; 0 for none.";
    }
    leaf listen-port {
      type uint32;
      description
        "For wireguard, the port the interface listens on.";
    }
    leaf recursive {
      type empty;
      description
        "For zfs, with those under it (-r).";
    }
    leaf force {
      type empty;
      description
        "For unmounting, though it is in use (-f).";
    }
    leaf metric {
      type uint32;
      description
        "For route, the cost of the route: of several to one
         destination the lowest is used (route -metric).";
    }
    leaf weight {
      type uint32;
      description
        "For route, its share among routes of the same metric to one
         destination (route -weight).";
    }
    leaf source {
      type string {
        length "0..64";
      }
      description
        "For route, the address of this host that what takes the route
         is sent from (route -ifa).";
    }
    leaf pkg-ip {
      type uint8 {
        range "min..6";
      }
      description
        "For pkg-upgrade, the repository reached over IPv4 only (4,
         pkg -4) or IPv6 only (6, pkg -6).";
    }
    leaf conn {
      type string {
        length "0..32";
      }
      description
        "For ipsec, the connection: letters, digits, - and _, kept in
         conf.d/arcana-<conn>.conf.";
    }
    leaf ipsec-mode {
      type string {
        length "0..9";
      }
      description
        "For ipsec conn, tunnel or transport.";
    }
    leaf local-ts {
      type string {
        length "0..512";
      }
      description
        "For ipsec conn, this side's traffic selectors with commas, as
         swanctl.conf(5) writes them (2001:db8::1[gre]); none says the
         address itself in transport mode, everything in tunnel mode.";
    }
    leaf remote-ts {
      type string {
        length "0..512";
      }
      description
        "For ipsec conn, the peer's traffic selectors, as local-ts.";
    }
    leaf pubkey {
      type string {
        length "0..1024";
      }
      description
        "For ipsec conn, the peer's public key in base64 (DER), as the
         ipsec network kind tells it of that host.";
    }
    leaf reqid {
      type uint32;
      description
        "For ipsec conn, the reqid of the ipsec(4) interface it serves:
         tunnel mode, its policies the interface's.  For if-create of an
         ipsec interface, the reqid it is made with.";
    }
    leaf start-action {
      type string {
        length "0..5";
      }
      description
        "For ipsec conn: start, up at once and kept up; trap, up with
         the first packet that needs it (the default); none, only by
         up.";
    }
    leaf local-id {
      type string {
        length "0..128";
      }
      description
        "For ipsec conn, this side's identity when it is not its
         address (behind NAT, the address it has there).";
    }
    leaf remote-id {
      type string {
        length "0..128";
      }
      description
        "For ipsec conn, the peer's identity, as local-id.";
    }
    leaf tunnelfib {
      type uint32;
      description
        "For if-set and if-create of a tunnel (gif, gre, vxlan, geneve,
         wg), the routing table its outer packets are sent by.";
    }
    leaf child {
      type string {
        length "0..32";
      }
      description
        "For ipsec child and unchild, the child's name under the
         connection conn: its mode, traffic, reqid and start are the
         child's.";
    }
    leaf local-cert {
      type string {
        length "0..128";
      }
      description
        "For ipsec conn, this host's certificate, a file in swanctl's
         x509 (its key in private or pkcs8), in place of the key
         arcana made it.";
    }
    leaf remote-cert {
      type string {
        length "0..128";
      }
      description
        "For ipsec conn, the peer's certificate, a file in swanctl's
         x509, in place of its public key.";
    }
    leaf remote-ca {
      type string {
        length "0..128";
      }
      description
        "For ipsec conn, a CA in swanctl's x509ca that signed the
         peer's certificate, which remote-id names, in place of its
         public key.";
    }
    leaf addressing {
      type string {
        length "0..8";
      }
      description
        "For if-set, how the interface gets its address: dhcp
         (dhclient, by rc.conf's DHCP word, so with persist), slaac
         (inet6 accept_rtadv and rtsol, kept in ifconfig_<if>_ipv6),
         static, which takes both off, or was: as it was before
         Arcana first set dhcp or slaac on it (rc.conf's two lines,
         DHCP and SLAAC, kept by the agent then), nothing when that
         was not kept (Mplify 119 §12.2.3.2, §12.2.3.3).  A safe
         change undone puts back what the interface had before it.";
    }
    leaf safe-wait {
      type uint32 {
        range "10..3600";
      }
      description
        "With safe: the seconds the change waits to be confirmed
         before it is undone, in place of the agent's own (-w); the
         console's rollback timer for the host.";
    }
    leaf dataset {
      type string {
        length "0..255";
      }
      description
        "For jail-conf, the jail's ZFS dataset.";
    }
    leaf snapshot {
      type string {
        length "0..255";
      }
      description
        "For jail-conf make, the base jail's snapshot it is made from.";
    }
    leaf copy {
      type string {
        length "0..8";
      }
      description
        "For jail-conf make, clone or send.";
    }
    leaf path {
      type string {
        length "0..1024";
      }
      description
        "For jail-conf, the jail's root, its dataset's mountpoint; for
         cert, the certificate's file name.";
    }
    leaf text {
      type string {
        length "0..65536";
      }
      description
        "For jail-conf, a file's whole content; for cert add, the
         certificate as PEM.";
    }
    leaf start {
      type empty;
      description
        "For jail-conf make, the jail started once made.";
    }
    leaf preshared-key {
      type string {
        length "0..44";
      }
      description
        "For wireguard peer, the peer's preshared key, 44 characters of
         base64: given to wg(8) in a file of the agent's that is there
         only while it is read, and in no title nor trace.";
    }
    leaf lladdr {
      type string {
        length "0..17";
      }
      description
        "For neighbour add, the link address, six bytes of hex.";
    }
    leaf temporary {
      type empty;
      description
        "For neighbour add, one that ages out as the others do.";
    }
    leaf user {
      type string {
        length "0..32";
      }
      description
        "For ssh authorize, unauthorize and options, the user whose keys.";
    }
    leaf pkg-repo {
      type string {
        length "0..64";
      }
      description
        "For pkg-upgrade and pkg-install, the repository only (pkg -r),
         one of those pkg is configured with there.";
    }
    leaf release {
      type string {
        length "0..16";
      }
      description
        "A FreeBSD release to go to (jail-base upgrade: \"16\", the
         latest of that major, or \"15.2\"); for convert, the branch
         of the FreeBSD-base repository, the jail's own release when
         none.";
    }
    leaf-list accept {
      type string {
        length "0..32";
      }
      description
        "For service-action's enable and disable and service-config,
         written to Arcana's rc.conf file as a commit is: the warnings
         accepted (rc-conf-files, rc-conf-conflict), a commit's
         accept.";
    }
  }

  grouping set-job {
    description
      "A job, as the agent's queue keeps it; arcana-jobs has it now:
       kept a structure for the queue.";
    leaf id {
      type uint64;
    }
    leaf kind {
      type uint8 {
        range "0..50";
      }
      description
        "One of job-kind: 0 jail-action 1 address 2 service-action 3 service-config 4 pkg-upgrade 5 if-address 6 if-state 7 route 8 if-set 9 if-create 10 if-destroy 11 netgraph 12 wireguard 13 bird 14 if-vnet 15 kmod 16 zfs 17 zpool 18 mount 19 gpart 20 cam 21 sysctl 22 ipfw 23 bridge 24 geneve 25 process 26 pkg-clean 27 ipsec 28 pkg-install 29 ntp 30 rtadvd 31 ipsec-sa 32 jail-conf 33 neighbour 34 cert 35 ssh 36 carp 37 poudriere 38 clamav 39 suricata 40 nfs 41 iscsi 42 hast 43 sysfile 44 geom 45 smtpd 46 jail-allow 47 jail-base 48 reboot 49 speeder 50 monitor.";
    }
    leaf title {
      type string;
      description
        "What it does, in words.";
    }
    leaf state {
      type uint8 {
        range "0..4";
      }
      description
        "One of job-state: 0 queued 1 running 2 done 3 cancelled 4 unconfirmed.";
    }
    leaf ok {
      type boolean;
      description
        "With state done, whether it succeeded.";
    }
    leaf error {
      type string;
    }
    leaf created {
      type int64;
      description
        "Unix time it was queued.";
    }
    leaf started {
      type int64;
    }
    leaf finished {
      type int64;
    }
    leaf peer {
      type string;
      description
        "Who queued it.";
    }
    leaf confirm-by {
      type int64;
      description
        "With state unconfirmed, the Unix time it is undone at.";
    }
    leaf user {
      type string;
      description
        "Who asked for it, the request's NACM user; none for the recovery session.";
    }
  }

  sx:structure jail {
    cg:struct "jail";
    description
      "A jail, as the agent's jail.c reads it; arcana-jails has it now:
       kept a structure for the agent's own use.";
    uses set-jail;
  }

  sx:structure service {
    cg:struct "service";
    description
      "An rc.d script, as the agent's services.c reads it; arcana-services
       has it now: kept a structure for the agent's own use.";
    uses set-service;
  }

  sx:structure job-spec {
    cg:struct "job-spec";
    description
      "One change to queue; the attributes its kind needs.  arcana-jobs'
       submit carries it now, a change made one by the agent: kept a
       structure for the agent's queue.";
    uses set-job-spec;
  }

  sx:structure job {
    cg:struct "job";
    description
      "A job, as the agent's queue keeps it; arcana-jobs has it now:
       kept a structure for the queue.";
    uses set-job;
  }

}
