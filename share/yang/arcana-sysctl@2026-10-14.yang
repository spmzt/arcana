module arcana-sysctl {
  yang-version 1.1;
  namespace "urn:arcana:yang:arcana-sysctl";
  prefix arcsys;

  organization
    "Arcana";
  contact
    "Pouria Mousavizadeh Tehrani <pouria@FreeBSD.org>";
  description
    "FreeBSD's kernel state, sysctl(3): the values as sysctl(8) prints
     them, and what sysctl.conf(5) sets at boot, its configuration,
     written in place, every other line kept (libvarconf, read as
     sysctl(8)'s parsefile() reads it), and set in the kernel at once
     by a commit.";

  revision 2026-10-14 {
    description
      "Initial revision.";
  }

  container sysctl {
    description
      "The kernel's state.";
    list kept {
      key "name";
      ordered-by user;
      description
        "A setting of sysctl.conf(5), set at boot in its order.";
      leaf name {
        type string {
          pattern '[A-Za-z0-9_%.-]+';
        }
        description
          "The variable.";
      }
      leaf value {
        type string;
        mandatory true;
        description
          "Its value, as sysctl(8) takes it.";
      }
    }
    leaf total {
      type uint64;
      config false;
      description
        "How many values there are, when fewer are listed.";
    }
    list value {
      key "name";
      config false;
      description
        "A value of the kernel's, where the tree was asked from.";
      leaf name {
        type string;
        description
          "Its name.";
      }
      leaf value {
        type string;
        description
          "Its value, as sysctl(8) prints it.";
      }
      leaf type {
        type string;
        description
          "Its kind: integer, string, opaque, ...";
      }
      leaf writable {
        type boolean;
        description
          "Whether it can be set.";
      }
      leaf description {
        type string;
        description
          "What it is said to be (sysctl -d).";
      }
      leaf tunable {
        type boolean;
        description
          "Whether the loader sets it too, from loader.conf(5)
           (CTLFLAG_TUN): one not writable is set there alone.";
      }
    }
    action read {
      description
        "The values whose names begin with prefix, in the kernel's
         order, as many as count, from the one after after: the tree
         read a part at a time.";
      input {
        leaf prefix {
          type string {
            length "0..200";
            pattern '[A-Za-z0-9_%.-]*';
          }
          description
            "Where in the tree: a name, or the start of one.  A name
             the kernel leaves out of its list (an old name for
             another) is found when asked for by itself.";
        }
        leaf after {
          type string {
            length "1..256";
          }
          description
            "Go on after this one, the last of the part before, as
             the kernel names it (a name may have blanks).";
        }
        leaf count {
          type uint16 {
            range "1..4000";
          }
          default "4000";
          description
            "How many at most.";
        }
        leaf jail {
          type string;
          description
            "A vnet jail's network's, under net., as its own sysctl(8)
             prints them: name and value each, in one part.";
        }
      }
      output {
        list value {
          description
            "A value of the kernel's.";
          leaf name {
            type string;
            description
              "Its name.";
          }
          leaf value {
            type string;
            description
              "Its value, as sysctl(8) prints it.";
          }
          leaf type {
            type string;
            description
              "Its kind: integer, string, unsigned, ...";
          }
          leaf writable {
            type boolean;
            description
              "Whether it can be set.";
          }
          leaf tunable {
            type boolean;
            description
              "Whether the loader sets it too (CTLFLAG_TUN).";
          }
          leaf description {
            type string;
            description
              "What it is said to be (sysctl -d).";
          }
        }
        leaf next {
          type string;
          description
            "There are more: the after of the next part.";
        }
        leaf total {
          type uint64;
          description
            "How many there are under prefix, when count left some
             out of a read from the start.";
        }
      }
    }
  }
  container boot {
    description
      "What the loader sets for the next boot (loader.conf(5)): kernel
       tunables, kept in /boot/loader.conf.d/arcana.conf, Arcana's
       file, every other line kept.  The loader reads it after
       /boot/loader.conf, so a tunable set in both is ours, and
       before /boot/loader.conf.local, which wins over it.";
    list tunable {
      key "name";
      description
        "A tunable of the kernel's environment, set by the loader.  A
         name without a dot is the loader's own (a module's _load) and
         is left as it is, not listed.  net.fibs is never lowered: the
         FIBs the kernel has stay.";
      leaf name {
        type string {
          length "1..200";
          pattern '[A-Za-z0-9][A-Za-z0-9_-]*([.][A-Za-z0-9_-]+)+';
        }
        description
          "The tunable, as the kernel names it (kern.racct.enable).";
      }
      leaf value {
        type string {
          length "0..1024";
        }
        mandatory true;
        description
          "Its value, as the loader takes it: a number of the kernel's
           type (with a k, m, g or t after it), or text.";
      }
      leaf running {
        type string;
        config false;
        description
          "The kernel's value now, as sysctl(8) prints it; none where
           the kernel has no such sysctl.";
      }
      leaf pending {
        type boolean;
        config false;
        description
          "The value differs from running: it takes hold at the next
           boot.";
      }
    }
  }
}
