module arcana-jails {
  yang-version 1.1;
  namespace "urn:arcana:yang:arcana-jails";
  prefix arcj;

  import ietf-netconf-acm {
    prefix nacm;
    reference
      "RFC 8341: Network Configuration Access Control Model";
  }

  import ietf-logical-network-element {
    prefix lne;
    reference
      "RFC 8530: YANG Model for Logical Network Elements";
  }

  organization
    "Arcana";
  contact
    "Pouria Mousavizadeh Tehrani <pouria@FreeBSD.org>";
  description
    "FreeBSD's jails (jail(8), jail(2)): those jail.conf(5) and the
     files in jail.conf.d define, as jail(8) -e resolves them, and
     those running, as jail_get(2) gives them (jls(8)); and what is
     done to one: started, stopped, restarted (jail(8) -c, -r, -rc,
     with the configuration's scripts) or killed (jail_remove(2),
     without them).

     A jail with a vnet of its own (jail(8)'s vnet) is also a logical
     network element (RFC 8530): lne names it.

     Running is each jail's parameters as its configuration file has
     them, and whether rc.d/jail starts it at boot (rc.conf(5)'s
     jail_enable and jail_list).  A commit writes what differs: a
     parameter in the jail's block of its file, in place, every other
     line kept (libjailconf); a jail not there before as a block of
     its own in jail.conf.d; jail_list and jail_enable in Arcana's
     rc.conf file.  The running jail is left as it is: the actions
     change that.";

  revision 2026-10-14 {
    description
      "Initial revision.";
  }

  typedef jail-state {
    type enumeration {
      enum running {
        value 0;
        description
          "jail_get(2) finds it, not dying.";
      }
      enum stopped {
        value 1;
        description
          "Configured, not running.";
      }
      enum dying {
        value 2;
        description
          "Removed, its last references not yet gone (jls(8) -d).";
      }
      enum absent {
        value 3;
        description
          "Neither configured nor running.";
      }
    }
    description
      "Where a jail is in its life.";
  }

  grouping after {
    description
      "The jail as it is after an action.";
    leaf state {
      type jail-state;
      description
        "Its state.";
    }
    leaf jid {
      type uint32;
      description
        "Its number, while it runs.";
    }
  }

  container jails {
    description
      "The host's jails.";
    leaf-list scope {
      type string;
      config false;
      description
        "The configuration files jail(8) is run with (-f):
         /etc/jail.conf and those of /etc/jail.conf.d.";
    }
    list conf-error {
      config false;
      description
        "A configuration file jail(8) could not read, and why.";
      leaf scope {
        type string;
        description
          "The file.";
      }
      leaf message {
        type string;
        description
          "What jail(8) said of it.";
      }
    }
    list jail {
      key "name";
      description
        "A jail, configured or running or both.";
      leaf name {
        type string {
          length "1..255";
        }
        description
          "Its name (jail(8)'s name; a child's parent.child).";
      }
      leaf boot {
        type boolean;
        description
          "Started at boot by rc.d/jail: jail_enable is yes and
           jail_list is empty or names it.  Written as the list of
           the jails started, never an empty list that starts every
           jail; with none, jail_enable is no.";
      }
      leaf scope {
        type string;
        description
          "The configuration file that defines it.  A jail not there
           before is written to jail.conf.d/<name>.conf; one defined
           is not moved.";
      }
      list param {
        key "name";
        description
          "Every parameter its configuration gives it, as jail(8) -e
           resolves them (variables expanded, += appended).  One
           changed is set in the jail's own block, where the first
           statement of it was or last; one taken out goes with its
           statements, unless the block has none, inherited from the
           file's defaults: that is refused.";
        leaf name {
          type string;
          description
            "The parameter, as jail(8) names it.";
        }
        leaf-list value {
          type string;
          ordered-by user;
          description
            "Its values; none for a boolean set.";
        }
      }
      leaf state {
        type jail-state;
        config false;
        description
          "Where it is in its life.";
      }
      leaf jid {
        type uint32;
        config false;
        description
          "Its number (jid), while it runs.";
      }
      leaf configured {
        type boolean;
        config false;
        description
          "Whether a configuration file defines it.";
      }
      leaf hostname {
        type string;
        config false;
        description
          "host.hostname.";
      }
      leaf path {
        type string;
        config false;
        description
          "Its root directory (path).";
      }
      leaf-list ip4 {
        type string;
        config false;
        ordered-by user;
        description
          "ip4.addr, as jail(8) has each: an address, with an
           interface and a prefix length where given.";
      }
      leaf-list ip6 {
        type string;
        config false;
        ordered-by user;
        description
          "ip6.addr, as ip4.";
      }
      leaf vnet {
        type boolean;
        config false;
        description
          "Whether it has a network stack of its own (vnet = new).";
      }
      leaf osrelease {
        type string;
        config false;
        description
          "The release it says it is (osrelease).";
      }
      leaf persist {
        type boolean;
        config false;
        description
          "Whether it stays without processes (persist).";
      }
      leaf securelevel {
        type int32;
        config false;
        description
          "Its securelevel (securelevel(7)).";
      }
      leaf parent {
        type uint32;
        config false;
        description
          "The jid of the jail it is in; 0, the host.";
      }
      leaf children {
        type uint32;
        config false;
        description
          "How many jails it has in it now.";
      }
      leaf nproc {
        type uint32;
        config false;
        description
          "Its processes now.";
      }
      leaf rss {
        type uint64;
        units "kibibytes";
        config false;
        description
          "Their resident memory, kinfo_proc's ki_rssize summed.";
      }
      leaf cpu {
        type decimal64 {
          fraction-digits 2;
        }
        units "percent";
        config false;
        description
          "Their share of one CPU, kinfo_proc's ki_pctcpu summed.";
      }
      leaf interface {
        type string;
        config false;
        description
          "interface: the one its addresses are added to.";
      }
      leaf-list allow {
        type string;
        config false;
        description
          "Of a running jail: its allow.* parameters as the kernel has
           them, each allow.name=0|1.";
      }
      leaf-list plugin {
        type string;
        config false;
        description
          "Of a running jail with a network of its own: the plugins it
           has, as a host's, by the programs installed in it.";
      }
      leaf lne {
        type leafref {
          path "/lne:logical-network-elements/lne:logical-network-element"
             + "/lne:name";
          require-instance false;
        }
        config false;
        description
          "The logical network element it is, with a vnet of its own.";
      }
      list dying {
        key "jid";
        config false;
        description
          "Earlier jails of this name the kernel still has, dying (jls
           -d), while one of the name runs or is defined: a jail
           removed whose sockets or mounts hold it.  A dying jail with
           no other of its name is the entry itself, state dying.";
        leaf jid {
          type uint32;
          description
            "Its jail ID.";
        }
        leaf path {
          type string;
          description
            "Its root.";
        }
      }
      action start {
        nacm:default-deny-all;
        description
          "jail(8) -c with its configuration: its exec.prestart,
           exec.start and the rest run.";
        output {
          uses after;
        }
      }
      action stop {
        nacm:default-deny-all;
        description
          "jail(8) -r: its exec.stop and the rest run, then
           jail_remove(2).";
        output {
          uses after;
        }
      }
      action restart {
        nacm:default-deny-all;
        description
          "jail(8) -rc.";
        output {
          uses after;
        }
      }
      action kill {
        nacm:default-deny-all;
        description
          "jail_remove(2), without its stop scripts.";
        output {
          uses after;
        }
      }
    }
  }
}
