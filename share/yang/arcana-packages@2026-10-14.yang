module arcana-packages {
  yang-version 1.1;
  namespace "urn:arcana:yang:arcana-packages";
  prefix arcpkg;

  import ietf-netconf-acm {
    prefix nacm;
    reference
      "RFC 8341: Network Configuration Access Control Model";
  }

  import cblink-gen {
    prefix cg;
  }
  import arcana-jails {
    prefix arcj;
  }

  organization
    "Arcana";
  contact
    "Pouria Mousavizadeh Tehrani <pouria@FreeBSD.org>";
  description
    "FreeBSD's packages (pkg(8)): those installed on the host, or in a
     running jail, as pkg's own database has them (pkg query), each
     with the version its repository has where that is newer (pkg
     version -vRl '<'); the catalogue refreshed (pkg update) and
     packages upgraded (pkg upgrade) as actions.

     A jail's packages are the jail's: arcana-jails's jail has them.";

  revision 2026-10-14 {
    description
      "Initial revision.";
  }

  typedef ip-version {
    type enumeration {
      enum any {
        value 0;
        description
          "pkg's own choice.";
      }
      enum ipv4 {
        value 4;
        description
          "pkg -4.";
      }
      enum ipv6 {
        value 6;
        description
          "pkg -6.";
      }
    }
    description
      "How pkg reaches its repository.";
  }

  grouping package {
    description
      "A package.";
    leaf name {
      type string;
      description
        "Its name (pkg's name, without its version).";
    }
    leaf installed {
      type string;
      description
        "The version installed.";
    }
    leaf available {
      type string;
      description
        "A newer version the repository has, when it was asked.";
    }
    leaf automatic {
      type boolean;
      description
        "Whether it came as another's dependency (pkg's automatic
         flag).";
    }
    leaf comment {
      type string;
      description
        "Its one-line description.";
    }
    leaf size {
      type uint64;
      units "bytes";
      description
        "What it takes installed.";
    }
    leaf origin {
      type string;
      description
        "Its port, category/name.";
    }
  }

  grouping listed {
    description
      "The packages read, with where they come from.";
    list package {
      cg:struct "package";
      key "name";
      description
        "A package.";
      uses package;
    }
    leaf-list repository {
      type string;
      description
        "The repositories pkg is configured with there (pkg -vv),
         enabled or not: an upgrade may be held to any of them.";
    }
    leaf pkgbase {
      type boolean;
      description
        "Of a jail: whether its base system is pkgbase
         (FreeBSD-runtime is one of its packages).";
    }
  }

  grouping packages {
    description
      "The packages of a host or of a jail, and what is done to them.";
    container packages {
      cg:struct "packages";
      config false;
      description
        "Its packages: those installed (pkg query), read with the
         host's; a jail's by its read action.";
      uses listed;
      action read {
        nacm:default-deny-all;
        description
          "The packages installed, from pkg's own database (pkg
           query), without asking the repository: a jail's, which a
           read of the jails leaves out.";
        output {
          uses listed;
        }
      }
      action refresh {
        nacm:default-deny-all;
        description
          "What the repository has newer (pkg version -vRl '<'), after
           pkg update with update.  A repository of packages built for
           a newer FreeBSD is refused by pkg, the error naming
           IGNORE_OSVERSION; with ignore-osversion the read goes past
           it.";
        input {
          leaf ip-version {
            type ip-version;
            default "any";
            description
              "How the repository is reached.";
          }
          leaf update {
            type boolean;
            default "false";
            description
              "pkg update first: the catalogue read again.";
          }
          leaf ignore-osversion {
            type boolean;
            default "false";
            description
              "Past a repository for a newer FreeBSD
               (IGNORE_OSVERSION).";
          }
        }
        output {
          uses listed;
        }
      }
      action upgrade {
        nacm:default-deny-all;
        description
          "pkg upgrade -y, of the packages named or of all.";
        input {
          leaf-list name {
            type string;
            description
              "The packages; none, all of them.";
          }
          leaf dry-run {
            type boolean;
            default "false";
            description
              "Only what pkg would do (pkg upgrade -n).";
          }
          leaf ignore-osversion {
            type boolean;
            default "false";
            description
              "Packages built for a newer FreeBSD too
               (IGNORE_OSVERSION).";
          }
          leaf ip-version {
            type ip-version;
            default "any";
            description
              "How the repository is reached.";
          }
          leaf repository {
            type string;
            description
              "From this one of pkg's repositories alone (pkg upgrade
               -r); none, from where pkg's configuration has each.";
          }
          leaf every-jail {
            type boolean;
            default "false";
            description
              "Of the host's: in every running jail that has pkg
               instead, one after the other, a jail that fails not
               stopping the others, which the error names.";
          }
        }
        output {
          leaf upgraded {
            type uint32;
            description
              "How many were upgraded, or would be.";
          }
          list package {
            cg:struct "package";
            key "name";
            description
              "Those still pending after it: the version installed,
               and the one the repository has as available.";
            uses package;
          }
        }
      }
    }
  }

  uses packages;

  augment "/arcj:jails/arcj:jail" {
    description
      "A running jail's packages.";
    uses packages;
  }
}
