module arcana-history {
  yang-version 1.1;
  namespace "urn:arcana:yang:arcana-history";
  prefix archist;

  import cblink-gen {
    prefix cg;
  }
  import ietf-yang-types {
    prefix yang;
    reference
      "RFC 9911: Common YANG Data Types";
  }

  organization
    "Arcana";
  contact
    "Pouria Mousavizadeh Tehrani <pouria@FreeBSD.org>";
  description
    "How busy a FreeBSD host has been, which the agent samples by
     itself and keeps the last of: CPU (kern.cp_time), the load
     average (getloadavg(3)), memory and swap in use (vm.stats.vm,
     kvm_getswapinfo(3)), bytes a second in and out of each interface
     but the loopback (getifaddrs(3)) and read from and written to
     each disk (devstat(3)), and each running jail's share of a CPU
     and memory as the kernel's resource accounting has them
     (rctl(8), kern.racct.enable=1), and each FEC relay's (UDPspeeder,
     net/udpspeeder) rates as its --report lines in syslog(3) have
     them.  How it samples (step, keep) and
     the limits above which an event (threshold) is made are
     configuration, kept for the agent's next start; the samples are
     state, written down when the agent stops and read again when it
     starts.  The history operation of arcana.yaml converted (Y-3).";

  revision 2026-10-15 {
    description
      "Initial revision.";
  }

  typedef percent {
    type decimal64 {
      fraction-digits 1;
      range "0..100";
    }
    description
      "A percentage.";
  }

  grouping sample {
    description
      "One sample.";
    leaf time {
      type yang:date-and-time;
      description
        "When it was taken.";
    }
    leaf cpu {
      type percent;
      description
        "CPU busy, of all CPUs.";
    }
    leaf load {
      type decimal64 {
        fraction-digits 2;
      }
      description
        "The one-minute load average.";
    }
    leaf memory {
      type uint64;
      units "bytes";
      description
        "Memory in use.";
    }
    leaf swap {
      type uint64;
      units "bytes";
      description
        "Swap in use.";
    }
    leaf received {
      type uint64;
      units "bytes/second";
      description
        "Received on all interfaces but the loopback.";
    }
    leaf sent {
      type uint64;
      units "bytes/second";
      description
        "Sent on them.";
    }
    leaf read {
      type uint64;
      units "bytes/second";
      description
        "Read from all disks.";
    }
    leaf written {
      type uint64;
      units "bytes/second";
      description
        "Written to them.";
    }
    list interface {
      key "name";
      description
        "Each interface told apart, at most 16.";
      leaf name {
        type string;
        description
          "The interface.";
      }
      leaf received {
        type uint64;
        units "bytes/second";
        description
          "In.";
      }
      leaf sent {
        type uint64;
        units "bytes/second";
        description
          "Out.";
      }
    }
    list disk {
      key "name";
      description
        "Each disk told apart, at most 16.";
      leaf name {
        type string;
        description
          "The disk.";
      }
      leaf read {
        type uint64;
        units "bytes/second";
        description
          "Read.";
      }
      leaf written {
        type uint64;
        units "bytes/second";
        description
          "Written.";
      }
    }
    list jail {
      key "name";
      description
        "Each running jail told apart, at most 16, as the kernel's
         resource accounting has it.";
      leaf name {
        type string;
        description
          "The jail.";
      }
      leaf cpu {
        type percent;
        description
          "Its share of one CPU.";
      }
      leaf memory {
        type uint64;
        units "bytes";
        description
          "Its memory.";
      }
    }
    list relay {
      key "name";
      description
        "Each FEC relay told apart, at most 16, by its syslog tag:
         arcana_relay, or arcana_relay_<profile> for one of several
         (Arcana's rc script's), or speederv2, the admin's.  Its
         figures are those of its last --report interval, both ways
         summed, while its last report is fresh; zero else.";
      leaf name {
        type string;
        description
          "The relay's tag.";
      }
      leaf plain {
        type uint64;
        units "bytes/second";
        description
          "Taken in plain: the tunnel's traffic as the relay carries
           it.";
      }
      leaf added {
        type uint64;
        units "bytes/second";
        description
          "Added to it by the FEC: its overhead, the redundant packets
           and their headers.";
      }
    }
  }

  grouping history-settings {
    description
      "How the agent samples, and its limits.";
    container sampling {
      description
        "How the agent samples, kept for its next start: an hour
         every five seconds until told otherwise.";
      leaf step {
        type uint16 {
          range "1..3600";
        }
        units "seconds";
        default "5";
        description
          "Seconds between two samples.";
      }
      leaf keep {
        type uint32 {
          range "0..5000";
        }
        default "720";
        description
          "How many samples are kept; 0, none taken.";
      }
      leaf hold {
        type uint16 {
          range "0..3600";
        }
        units "seconds";
        default "60";
        description
          "How long a figure stays over its limit before it is over
           (an event, threshold, and for cpu, memory and storage a
           fault), and under it again before it is back under; 0, at
           the first sample that crosses.  The limits below and the
           rules alike.";
      }
      leaf enabled {
        type boolean;
        default "true";
        description
          "Whether the host is sampled at all.  Off, no sample is
           taken, no limit judged and no event or fault made of one;
           a resource fault raised before is cleared once; the
           samples kept stay, to be read, until it is on again.";
      }
    }
    container limits {
      description
        "The percentages above which an event (threshold) is made,
         either way across; 0 none.";
      leaf cpu {
        type uint8 {
          range "0..100";
        }
        description
          "CPU busy.";
      }
      leaf memory {
        type uint8 {
          range "0..100";
        }
        description
          "Memory in use, of the whole.";
      }
      leaf swap {
        type uint8 {
          range "0..100";
        }
        description
          "Swap in use, of the whole.";
      }
      leaf storage {
        type uint8 {
          range "0..100";
        }
        description
          "A file system full (a ZFS pool's allocated share, another
           local one's as df has it), looked at each minute; over it
           also a storage fault.";
      }
    }
    list rule {
      key "kind name";
      description
        "A limit of one interface, disk or jail.";
      leaf kind {
        type enumeration {
          enum net {
            description
              "An interface: bytes a second, in and out together.";
          }
          enum disk {
            description
              "A disk: bytes a second, read and written together.";
          }
          enum jail-cpu {
            description
              "A jail's share of one CPU, in percent.";
          }
          enum jail-mem {
            description
              "A jail's memory, in bytes.";
          }
        }
        description
          "What is limited.";
      }
      leaf name {
        type string;
        description
          "The interface's, the disk's or the jail's name.";
      }
      leaf limit {
        type uint64;
        description
          "The limit, in the kind's unit.";
      }
      leaf over {
        type boolean;
        config false;
        description
          "Over it at the last sample.";
      }
    }
  }

  grouping history-totals {
    description
      "The sampler as it is, but its samples.";
    leaf bytes {
      type uint64;
      units "bytes";
      description
        "The memory the samples take.";
    }
    leaf ncpu {
      type uint16;
      description
        "How many CPUs the host has.";
    }
    leaf memory-total {
      type uint64;
      units "bytes";
      description
        "The host's memory.";
    }
    leaf swap-total {
      type uint64;
      units "bytes";
      description
        "Its swap.";
    }
    leaf racct {
      type boolean;
      description
        "The kernel accounts resources per jail
         (kern.racct.enable).";
    }
    leaf-list interface {
      type string;
      description
        "The interfaces told apart.";
    }
    leaf-list disk {
      type string;
      description
        "The disks told apart.";
    }
    leaf-list jail {
      type string;
      description
        "The jails told apart.";
    }
    leaf-list relay {
      type string;
      description
        "The FEC relays told apart.";
    }
  }

  container history {
    description
      "The sampler and what it kept.";
    uses history-settings;
    container state {
      config false;
      description
        "The sampler as it is.";
      uses history-totals;
      list sample {
        cg:struct "sample";
        key "time";
        description
          "The samples kept, oldest first.";
        uses sample;
      }
    }
    action read {
      description
        "The samples after a time, with how they are taken and the
         sampler as it is: what a page that has the ones before asks
         for.";
      input {
        leaf after {
          type yang:date-and-time;
          description
            "Only samples taken after this.";
        }
      }
      output {
        uses history-settings;
        uses history-totals;
        list sample {
          cg:struct "sample";
          key "time";
          description
            "The samples, oldest first.";
          uses sample;
        }
      }
    }
  }
}
