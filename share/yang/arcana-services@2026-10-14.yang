module arcana-services {
  yang-version 1.1;
  namespace "urn:arcana:yang:arcana-services";
  prefix arcsvc;

  import ietf-netconf-acm {
    prefix nacm;
    reference
      "RFC 8341: Network Configuration Access Control Model";
  }

  organization
    "Arcana";
  contact
    "Pouria Mousavizadeh Tehrani <pouria@FreeBSD.org>";
  description
    "FreeBSD's services: the rc.d scripts of rc(8) (/etc/rc.d and
     /usr/local/etc/rc.d), each enabled by its rcvar in rc.conf(5) and
     set by its other rc.conf variables, as service(8) and sysrc(8)
     see them; and what is done to one, started, stopped, restarted or
     reloaded (service(8)).

     A service is there because its script is: an entry names a script
     the host has.  Its configuration is rc.conf's, changed in place,
     every other line kept; its state is what the script says.";

  revision 2026-10-14 {
    description
      "Initial revision.";
  }

  grouping now {
    description
      "What the script's status command says of the service.";
    leaf running {
      type boolean;
      config false;
      description
        "Whether it runs (service <name> status); absent when not
         asked.";
    }
    leaf pid {
      type uint32;
      config false;
      description
        "Its process, while it runs.";
    }
    leaf status {
      type string;
      config false;
      description
        "The status line, as the script printed it.";
    }
  }

  container services {
    description
      "The host's rc.d scripts.";
    action convert {
      nacm:default-deny-all;
      description
        "The services' rc.conf configuration moved under Arcana, as
         running reads it: each named service's <name>_enable and
         <name>_* variables, as the files rc(8) reads set them, written
         to Arcana's file (/usr/local/etc/rc.conf.d/arcana) and
         commented out where they are in yours ('#var=\"value\"  # taken
         by Arcana'), the line kept.  A commit's rules apply: what you
         have not accepted (rc-conf-files, rc-conf-conflict) is refused
         with its error-app-tag; failing, every file is put back.
         The output lists what was taken, or with dry-run what would
         be, each variable with the file and line it was in.";
      input {
        leaf-list service {
          type string {
            pattern '[A-Za-z0-9_][A-Za-z0-9_.-]*';
          }
          description
            "The services to convert; none named, every script the
             host has.";
        }
        leaf dry-run {
          type boolean;
          default false;
          description
            "Say what would be taken, writing nothing.";
        }
      }
      output {
        list service {
          key "name";
          description
            "A service with variables in your files.";
          leaf name {
            type string;
            description
              "The script's name.";
          }
          list variable {
            key "name file line";
            description
              "A variable of yours taken, or to be taken, from its
               file and line.";
            leaf name {
              type string;
              description
                "The variable.";
            }
            leaf file {
              type string;
              description
                "The file of yours that sets it.";
            }
            leaf line {
              type uint32;
              description
                "Its line in the file.";
            }
            leaf value {
              type string;
              description
                "Its value there, as rc(8) reads it.";
            }
            leaf left {
              type string;
              description
                "Why it was left where it is: its value is not a
                 literal (an expansion), or sh(1) may or may not run
                 the line; absent when taken.";
            }
          }
        }
      }
    }
    action release {
      nacm:default-deny-all;
      description
        "convert's inverse: the named services' rc.conf configuration
         given back to your files.  Each <name>_* variable is removed
         from Arcana's file (/usr/local/etc/rc.conf.d/arcana), and every
         line of yours convert commented out for one ('#var=\"value\"
         # taken by Arcana') put back as it was, in the files rc(8)
         reads for the service; one convert took off a shared line
         comes back on a line of its own.  A variable with no line of
         yours to put back is only dropped: its value falls back to
         what your files or the defaults say.  All or nothing: a marked
         line that would not read back as it was refuses the request,
         and failing, every file is put back.";
      input {
        leaf-list service {
          type string {
            pattern '[A-Za-z0-9_][A-Za-z0-9_.-]*';
          }
          min-elements 1;
          description
            "The services to give back.";
        }
        leaf dry-run {
          type boolean;
          default false;
          description
            "Say what would be given back, writing nothing.";
        }
      }
      output {
        list service {
          key "name";
          description
            "A service named, each variable of it Arcana's file set or
             your files had commented out for it; none, nothing to give
             back.";
          leaf name {
            type string;
            description
              "The service's name.";
          }
          list variable {
            key "name";
            description
              "A variable given back, or to be.";
            leaf name {
              type string;
              description
                "The variable.";
            }
            leaf arcana-value {
              type string;
              description
                "Its value in Arcana's file, removed; absent when
                 Arcana's file did not set it.";
            }
            list restored {
              key "file line";
              description
                "A line of yours put back.";
              leaf file {
                type string;
                description
                  "The file.";
              }
              leaf line {
                type uint32;
                description
                  "Its line there.";
              }
              leaf value {
                type string;
                description
                  "Its value, as rc(8) reads it; absent when not a
                   literal.";
              }
            }
            leaf dropped {
              type string;
              description
                "Present when no line of yours was put back: what its
                 value falls back to.";
            }
            leaf differs {
              type string;
              description
                "Present when the value rc(8) reads now is not
                 Arcana's: both values.";
            }
          }
        }
      }
    }
    list service {
      key "name";
      description
        "An rc.d script.";
      leaf name {
        type string {
          pattern '[A-Za-z0-9_][A-Za-z0-9_.-]*';
        }
        description
          "The script's name, as service(8) takes it.";
      }
      leaf enabled {
        type boolean;
        description
          "Its rcvar, YES or NO in rc.conf (sysrc(8)).";
      }
      list variable {
        key "name";
        description
          "One of its rc.conf variables (name_flags, name_program,
           ...), as sysrc(8) reads it; one set, written in place.";
        leaf name {
          type string {
            pattern '[A-Za-z_][A-Za-z0-9_]*';
          }
          description
            "The variable.";
        }
        leaf value {
          type string;
          description
            "Its value.";
        }
      }
      leaf path {
        type string;
        config false;
        description
          "The script, in /etc/rc.d or /usr/local/etc/rc.d.";
      }
      leaf rcvar {
        type string;
        config false;
        description
          "The rc.conf variable that enables it, if it has one.";
      }
      uses now;
      leaf description {
        type string;
        config false;
        description
          "What the script says of itself (service describe).";
      }
      leaf-list command {
        type string;
        config false;
        description
          "The script's extra commands (service extracommands).";
      }
      action start {
        nacm:default-deny-all;
        description
          "service <name> start.";
        output {
          uses now;
        }
      }
      action stop {
        nacm:default-deny-all;
        description
          "service <name> stop.";
        output {
          uses now;
        }
      }
      action restart {
        nacm:default-deny-all;
        description
          "service <name> restart.";
        output {
          uses now;
        }
      }
      action reload {
        nacm:default-deny-all;
        description
          "service <name> reload.";
        output {
          uses now;
        }
      }
      action read {
        description
          "The service as it is now, without the others' status read:
           whether rc(8) starts it at boot (service <name> enabled, by
           its rcvar, the defaults included), whether it runs, what it
           says of itself and its extra commands.";
        output {
          leaf enabled {
            type boolean;
            description
              "Whether rc(8) starts it at boot.";
          }
          leaf path {
            type string;
            description
              "The script.";
          }
          leaf rcvar {
            type string;
            description
              "The rc.conf variable that enables it, if it has one.";
          }
          uses now;
          leaf description {
            type string;
            description
              "What the script says of itself (service describe).";
          }
          leaf-list command {
            type string;
            description
              "The script's extra commands (service extracommands).";
          }
        }
      }
    }
  }
}
