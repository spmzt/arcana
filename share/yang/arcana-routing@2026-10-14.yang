module arcana-routing {
  yang-version 1.1;
  namespace "urn:arcana:yang:arcana-routing";
  prefix arcrt;

  import ietf-routing {
    prefix rt;
    reference
      "RFC 8349: A YANG Data Model for Routing Management (NMDA
       Version)";
  }
  import ietf-ospf {
    prefix ospf;
    reference
      "RFC 9129: YANG Data Model for the OSPF Protocol";
  }
  import ietf-rip {
    prefix rip;
    reference
      "RFC 8695: A YANG Data Model for the Routing Information
       Protocol (RIP)";
  }
  import ietf-isis {
    prefix isis;
    reference
      "RFC 9130: YANG Data Model for the IS-IS Protocol";
  }
  import ietf-babel {
    prefix babel;
    reference
      "RFC 9647: A YANG Data Model for the Babel Routing Protocol";
  }
  import ietf-bgp {
    prefix bgp;
    reference
      "draft-ietf-idr-bgp-model: YANG Model for Border Gateway
       Protocol (BGP-4), its revision 2026-08-14";
  }

  organization
    "Arcana";
  contact
    "Pouria Mousavizadeh Tehrani <pouria@FreeBSD.org>";
  description
    "The sources of FreeBSD's routes that ietf-routing (RFC 8349) has
     no identity for.

     A route's source-protocol is the origin netlink(4) gives it
     (rtm_protocol, RTPROT_* in <netlink/route/route.h>): the one the
     program that added it said, over netlink, or else what the
     kernel guesses from its flags (RTF_STATIC: static; RTF_PROTO1:
     zebra; the kernel's own otherwise).  Static ones are rt:static;
     the kernel's own without a gateway, an interface's network, are
     rt:direct; a routing protocol's are its module's identity:
     RTPROT_OSPF ospf:ospfv2 for an IPv4 route, ospf:ospfv3 for an
     IPv6 one; RTPROT_RIP rip:ripv2 and rip:ripng likewise;
     RTPROT_ISIS isis:isis; RTPROT_BABEL babel:babel; RTPROT_BGP
     bgp:bgp; the others are these.";

  revision 2026-10-14 {
    description
      "Initial revision.";
  }

  identity freebsd-origin {
    base rt:routing-protocol;
    description
      "A route's origin as FreeBSD's netlink(4) says it.";
  }

  identity redirect {
    base freebsd-origin;
    description
      "An ICMP redirect (RTPROT_REDIRECT).";
  }

  identity kernel {
    base freebsd-origin;
    description
      "The kernel's own, with a gateway (RTPROT_KERNEL).";
  }

  identity router-advertisement {
    base freebsd-origin;
    description
      "A router advertisement's (RTPROT_RA): rtsold(8)'s.";
  }

  identity dhcp {
    base freebsd-origin;
    description
      "A DHCP client's (RTPROT_DHCP).";
  }

  identity zebra {
    base freebsd-origin;
    description
      "Zebra's (RTPROT_ZEBRA), or one flagged RTF_PROTO1 by another
       daemon over the routing socket.";
  }

  identity bird {
    base freebsd-origin;
    description
      "BIRD's (RTPROT_BIRD).";
  }

  identity other {
    base freebsd-origin;
    description
      "Another origin netlink(4) names, or none it names.";
  }
}
