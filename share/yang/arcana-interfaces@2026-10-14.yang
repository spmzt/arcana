module arcana-interfaces {
  yang-version 1.1;
  namespace "urn:arcana:yang:arcana-interfaces";
  prefix arcif;

  import ietf-interfaces {
    prefix if;
    reference
      "RFC 8343: A YANG Data Model for Interface Management";
  }
  import iana-if-type {
    prefix ianaift;
  }
  import ietf-if-extensions {
    prefix if-ext;
    reference
      "draft-ietf-netmod-intf-ext-yang: Common Interface Extension YANG
       Data Models";
  }
  import ietf-if-vlan-encapsulation {
    prefix if-vlan;
    reference
      "draft-ietf-netmod-sub-intf-vlan-model: Sub-interface VLAN YANG
       Data Models";
  }
  import ieee802-dot1q-types {
    prefix dot1q-types;
  }
  import ieee802-dot1ax-linkagg {
    prefix dot1ax;
    reference
      "IEEE Std 802.1AX: Link Aggregation";
  }
  import ietf-ip {
    prefix ip;
    reference
      "RFC 8344: A YANG Data Model for IP Management";
  }
  import ietf-inet-types {
    prefix inet;
    reference
      "RFC 9911: Common YANG Data Types";
  }
  import ieee802-dot1q-bridge {
    prefix dot1q;
    reference
      "IEEE Std 802.1Q: Bridges and Bridged Networks";
  }

  organization
    "Arcana";
  contact
    "Pouria Mousavizadeh Tehrani <pouria@FreeBSD.org>";
  description
    "What FreeBSD's interfaces have beyond RFC 8343 and the standard
     models that extend it, as ifconfig(8) shows and sets it: the
     driver's name, groups, the tunnel FIB, capabilities, media, an
     epair(4)'s other end in a vnet, and the parts of a vlan(4), a
     bridge(4) and a lagg(4).

     What a standard model has is there, not here:
     - the MTU (ifconfig(8) mtu, SIOCSIFMTU), FreeBSD's for both
       families, is ietf-ip's ipv4 mtu (RFC 8344); ipv6's is it or
       the lower one an RA set (arcana-ip-deviations), and
       ietf-if-extensions' max-frame-size is it with the link's
       header and frame check sequence;
     - the Ethernet address (ifconfig(8) ether, SIOCSIFLLADDR) is
       ietf-if-ethernet-like's mac-address, the hardware's
       (SIOCGHWADDR) its bia-mac-address, for the interfaces it
       applies to; a vlan's or a bridge's is its phys-address;
     - the FIB (ifconfig(8) fib, SIOCSIFFIB) is ietf-network-instance's
       bind-ni-name (RFC 8529): the instance whose FIB it is, none for
       FIB 0;
     - an epair(4) end's other end is ietf-if-extensions'
       peer-interface;
     - a vlan(4)'s tag (ifconfig(8) vlan, vlanproto) is
       ietf-if-vlan-encapsulation's outer-tag, c-vlan for 802.1Q and
       s-vlan for 802.1ad, its parent (vlandev) ietf-if-extensions'
       parent-interface; a tag the model cannot hold (0, 4095) is not
       there;
     - an Ethernet's medium, as far as IEEE 802.3 has it, is
       ieee802-ethernet-interface's: auto-negotiation (autoselect),
       duplex (full-duplex, half-duplex), the PMD (the active subtype's
       IEEE 802.3 PMD type, other where IEEE names none); the media
       words below, any interface's with a medium, are ifconfig(8)'s
       own;
     - a lagg(4) is IEEE 802.1AX's (ieee802-dot1ax-linkagg): a key
       group and an aggregation system each, named as it is, its
       interface's lag and each port's aggport naming the key group,
       with LACP's state where its protocol is lacp (SIOCGLAGG's
       lacp_opreq: the system's priority and address, the keys, the
       ports' numbers, priorities and states); its protocol, hash, and
       a port's priority and flags, FreeBSD's own, are below;
     - a bridge(4) is IEEE 802.1Q's (ieee802-dot1q-bridge): a bridge of
       its name and address, a customer VLAN bridge of one component,
       VLAN-unaware (d-bridge-component) or with vlanfilter a C-VLAN
       component, its members (BRDGGIFS) its bridge ports; a member's
       port number and point-to-point state (ptp, autoptp) its
       bridge-port's, and where ifconfig(8) stp turned the spanning
       tree on, ieee802-dot1q-rstp-bridge's rstp: its state and role
       (BSTP_IFSTATE_*, BSTP_ROLE_*; disabled, listening and blocking
       are RSTP's discarding), its port identifier (FreeBSD's priority
       0 to 240 IEEE's 0 to 15), its path cost (ifpathcost the fixed
       one), its edge (edge, autoedge); a member's other flags,
       FreeBSD's own, are below.

     Each leaf names the FreeBSD facility it is read from and written
     to.  A list or leaf-list the system orders is in the order the
     kernel gives.";

  revision 2026-10-14 {
    description
      "Initial revision.";
  }

  typedef capabilities {
    type bits {
      bit rxcsum {
        position 0;
      }
      bit txcsum {
        position 1;
      }
      bit netcons {
        position 2;
      }
      bit vlan-mtu {
        position 3;
      }
      bit vlan-hwtagging {
        position 4;
      }
      bit jumbo-mtu {
        position 5;
      }
      bit polling {
        position 6;
      }
      bit vlan-hwcsum {
        position 7;
      }
      bit tso4 {
        position 8;
      }
      bit tso6 {
        position 9;
      }
      bit lro {
        position 10;
      }
      bit wol-ucast {
        position 11;
      }
      bit wol-mcast {
        position 12;
      }
      bit wol-magic {
        position 13;
      }
      bit toe4 {
        position 14;
      }
      bit toe6 {
        position 15;
      }
      bit vlan-hwfilter {
        position 16;
      }
      bit nv {
        position 17;
      }
      bit vlan-hwtso {
        position 18;
      }
      bit linkstate {
        position 19;
      }
      bit netmap {
        position 20;
      }
      bit rxcsum-ipv6 {
        position 21;
      }
      bit txcsum-ipv6 {
        position 22;
      }
      bit hwstats {
        position 23;
      }
      bit txrtlmt {
        position 24;
      }
      bit hwrxtstmp {
        position 25;
      }
      bit mextpg {
        position 26;
      }
      bit txtls4 {
        position 27;
      }
      bit txtls6 {
        position 28;
      }
      bit vxlan-hwcsum {
        position 29;
      }
      bit vxlan-hwtso {
        position 30;
      }
      bit txtls-rtlmt {
        position 31;
      }
      bit rxtls4 {
        position 32;
      }
      bit rxtls6 {
        position 33;
      }
      bit ipsec {
        position 34;
      }
      bit geneve-hwcsum {
        position 35;
      }
      bit geneve-hwtso {
        position 36;
      }
    }
    description
      "An interface's capabilities: each bit the IFCAP_B_* of
       <net/if.h> at its position, named as <net/if_strings.h> names
       it, in lower case with '-' for '_'.  Those from 32 are
       if_capabilities2, read by SIOCGIFCAPNV.";
  }

  grouping media-word {
    description
      "A medium as ifconfig(8)'s media, mediaopt and mode take it.";
    leaf subtype {
      type string;
      description
        "The subtype's name in <net/if_media.h>'s descriptions, as
         ifconfig(8) shows it: 'autoselect', '1000baseT', '10Gbase-T'.";
    }
    leaf-list option {
      type string;
      description
        "Its options' names: 'full-duplex', 'flowcontrol'.";
    }
    leaf mode {
      type string;
      description
        "An IEEE 802.11 medium's mode: '11a', '11g', '11ng'.";
    }
  }

  augment "/if:interfaces/if:interface" {
    description
      "FreeBSD's own parts of an interface.";
    leaf driver-name {
      config false;
      type string;
      description
        "The name the driver gave it, which a rename does not change:
         sysctl net.link.generic.ifdata.<index>.drivername, as
         ifconfig(8) -D shows it.";
    }
    leaf-list group {
      type string {
        length "1..15";
        pattern '.*[^0-9]';
      }
      description
        "The groups it is in: SIOCGIFGROUP, ifconfig(8) group, among
         them those the kernel puts it in (a cloned interface's
         driver's), but 'all', which every interface is in.  A group's
         name does not end in a digit.";
    }
    leaf tunnel-fib {
      type uint32;
      description
        "A tunnel's FIB for its outer packets: SIOCGTUNFIB,
         SIOCSTUNFIB, ifconfig(8) tunnelfib.";
    }
    container tunnel {
      description
        "A tunnel's outer addresses, of a gif(4), gre(4) or me(4):
         SIOCGIFPSRCADDR and SIOCGIFPDSTADDR (their _IN6 forms for
         IPv6), ifconfig(8) tunnel.  No ratified model has an IP
         tunnel's endpoints; IANA's tunnel types (RFC 8675) name its
         kind, as its interface's type does.";
      leaf local {
        type inet:ip-address-no-zone;
        description
          "The address its outer packets are sent from.";
      }
      leaf remote {
        type inet:ip-address-no-zone;
        description
          "The address they are sent to.";
      }
    }
    leaf capabilities {
      type capabilities;
      description
        "The capabilities enabled: SIOCGIFCAP's ifr_curcap,
         SIOCGIFCAPNV, ifconfig(8)'s options.";
    }
    leaf capabilities-supported {
      config false;
      type capabilities;
      description
        "The capabilities the driver has: SIOCGIFCAP's ifr_reqcap,
         ifconfig(8) -m's capabilities.";
    }
    container media {
      description
        "Its medium, where the driver has one: SIOCGIFXMEDIA, as
         ifconfig(8) shows it.";
      container current {
        description
          "The medium set: SIOCSIFMEDIA, ifconfig(8) media, mediaopt,
           mode.";
        uses media-word;
      }
      container active {
        config false;
        description
          "The medium in use, as autoselect chose it.";
        uses media-word;
      }
      leaf status {
        config false;
        type enumeration {
          enum active {
            description
              "IFM_ACTIVE: a carrier.";
          }
          enum no-carrier {
            description
              "No IFM_ACTIVE.";
          }
          enum associated {
            description
              "An IEEE 802.11 station, IFM_ACTIVE: associated.";
          }
          enum running {
            description
              "An IEEE 802.11 interface in another mode, IFM_ACTIVE.";
          }
        }
        description
          "The link's status, where the driver knows it (IFM_AVALID).";
      }
      leaf-list supported {
        config false;
        type string;
        description
          "The media the driver offers, each as ifconfig(8) -m lists
           it: the subtype, then 'mediaopt' and the options, then
           'mode' and the mode.";
      }
    }
    leaf peer-vnet {
      config false;
      type boolean;
      description
        "Of an epair(4) end: whether the other end is in another
         network stack, a vnet jail's, where ifconfig(8) vnet moved it.
         The kernel tells no other end, but the two have one
         driver-name, 'epair' and the pair's unit, whatever they are
         called and wherever they are: no interface here has its
         driver-name.  Where one has, it is ietf-if-extensions'
         peer-interface (two interfaces may share a name, one back from
         a vnet jail, and the list has the first only).";
    }
  }

  augment "/if:interfaces/if:interface/ip:ipv4/ip:address" {
    description
      "An IPv4 address's other end, on a point-to-point interface.";
    leaf peer {
      type inet:ipv4-address-no-zone;
      description
        "The address of the far end of the link: ifconfig(8)'s
         'inet a dest b', SIOCAIFADDR's ifra_dstaddr, as getifaddrs(3)
         gives it where the interface is IFF_POINTOPOINT.  Configured
         with the address, and kept with it in rc.conf.";
    }
  }

  augment "/if:interfaces/if:interface/ip:ipv6/ip:address" {
    description
      "An IPv6 address's other end, on a point-to-point interface.";
    leaf peer {
      type inet:ipv6-address-no-zone;
      description
        "The address of the far end of the link: ifconfig(8)'s
         'inet6 a dest b', as getifaddrs(3) gives it where the
         interface is IFF_POINTOPOINT.";
    }
  }

  augment "/if:interfaces/if:interface/dot1ax:lag" {
    description
      "What a lagg(4) has beyond IEEE 802.1AX: SIOCGLAGG, SIOCSLAGG.";
    leaf protocol {
      type enumeration {
        enum none {
          value 0;
        }
        enum roundrobin {
          value 1;
        }
        enum failover {
          value 2;
        }
        enum loadbalance {
          value 3;
        }
        enum lacp {
          value 4;
        }
        enum broadcast {
          value 5;
        }
      }
      description
        "Its protocol, LAGG_PROTO_*: ifconfig(8) laggproto.";
    }
    leaf hash {
      type bits {
        bit l2 {
          position 0;
        }
        bit l3 {
          position 1;
        }
        bit l4 {
          position 2;
        }
      }
      description
        "The headers its flows are hashed by, LAGG_F_HASHL*:
         SIOCGLAGGFLAGS, ifconfig(8) lagghash.";
    }
  }

  augment "/if:interfaces/if:interface/dot1ax:aggport" {
    description
      "What a lagg(4)'s port has beyond IEEE 802.1AX.";
    leaf priority {
      config false;
      type uint32;
      description
        "Its priority among the ports, rp_prio: failover's order.";
    }
    leaf flags {
      config false;
      type bits {
        bit master {
          position 0;
        }
        bit stack {
          position 1;
        }
        bit active {
          position 2;
        }
        bit collecting {
          position 3;
        }
        bit distributing {
          position 4;
        }
      }
      description
        "Its state, LAGG_PORT_*, under every protocol.";
    }
  }

  augment "/if:interfaces/if:interface/dot1q:bridge-port" {
    description
      "What a bridge(4) member has beyond IEEE 802.1Q.";
    leaf flags {
      config false;
      type bits {
        bit learning {
          position 0;
          description
            "IFBIF_LEARNING: ifconfig(8) learn.";
        }
        bit discover {
          position 1;
          description
            "IFBIF_DISCOVER: ifconfig(8) discover.";
        }
        bit span {
          position 3;
          description
            "IFBIF_SPAN: a span port, ifconfig(8) span.";
        }
        bit sticky {
          position 4;
          description
            "IFBIF_STICKY: ifconfig(8) sticky.";
        }
        bit private {
          position 11;
          description
            "IFBIF_PRIVATE: ifconfig(8) private.";
        }
        bit qinq {
          position 12;
          description
            "IFBIF_QINQ: ifconfig(8) qinq.";
        }
      }
      description
        "Its flags IEEE 802.1Q has no leaf for: struct ifbreq's
         ifbr_ifsflags, at its positions.";
    }
  }

  augment "/if:interfaces/if:interface/if-ext:encapsulation/"
        + "if-ext:encaps-type/if-vlan:dot1q-vlan/if-vlan:dot1q-vlan" {
    description
      "What a vlan(4) has beyond its tag.";
    leaf pcp {
      type dot1q-types:priority-type;
      description
        "The priority it sends with in its tag: SIOCGVLANPCP,
         SIOCSVLANPCP, ifconfig(8) vlanpcp.";
    }
  }
}
