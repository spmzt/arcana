module arcana-sshd {
  yang-version 1.1;
  namespace "urn:arcana:yang:arcana-sshd";
  prefix arcsshd;

  import ietf-yang-types {
    prefix yang;
    reference
      "RFC 9911: Common YANG Data Types";
  }
  import cblink-gen {
    prefix cg;
  }

  organization
    "Arcana";
  contact
    "Pouria Mousavizadeh Tehrani <pouria@FreeBSD.org>";
  description
    "The base system's sshd(8) on a FreeBSD host, or in a jail of it,
     as the agent reads it: the settings that matter (sshd -T, or the
     file's where sshd_config says otherwise), the banner, the host
     keys with their certificates (ssh-keygen -l, -L), the users who
     may sign in with their authorized keys, and the user CAs trusted
     (TrustedUserCAKeys).  Changes are jobs of kind ssh (banner, set,
     sign, user-cas, authorize, unauthorize), each read by sshd -t
     first and put back in safe mode.  The ssh operation of
     arcana.yaml converted (Y-3): the host's sshd, and a jail's by
     the read action.";

  revision 2026-10-15 {
    description
      "Initial revision.";
  }

  grouping key {
    description
      "A public key.";
    leaf type {
      type string;
      description
        "Its type: ssh-ed25519, ecdsa-sha2-nistp256, rsa ...";
    }
    leaf bits {
      type uint16;
      description
        "Its size.";
    }
    leaf fingerprint {
      type string;
      description
        "Its SHA256 fingerprint.";
    }
    leaf comment {
      type string;
      description
        "Its comment.";
    }
  }

  grouping sshd {
    description
      "sshd, where it runs.";
    leaf config {
      type string;
      description
        "sshd_config, the file it reads.";
    }
    list setting {
      cg:struct "setting";
      key "name";
      description
        "The settings that matter here, as sshd -T says them.";
      leaf name {
        type string;
        description
          "The setting, lower case as sshd prints it.";
      }
      leaf-list value {
        type string;
        description
          "Its values.";
      }
    }
    leaf settings-from-file {
      type string;
      description
        "Why the settings are the file's, not sshd -T's, when they
         are.";
    }
    leaf banner {
      type string;
      description
        "The banner's text, when Banner names a file.";
    }
    list host-key {
      cg:struct "host-key";
      key "path";
      description
        "The host keys.";
      leaf path {
        type string;
        description
          "The key's file.";
      }
      uses key;
      container certificate {
        description
          "Its certificate, when one is there.";
        leaf kind {
          type string;
          description
            "host or user.";
        }
        leaf id {
          type string;
          description
            "The certificate's identity.";
        }
        leaf-list principal {
          type string;
          description
            "Whom it is for.";
        }
        leaf serial {
          type uint64;
          description
            "Its serial number.";
        }
        leaf valid-after {
          type yang:date-and-time;
          description
            "Valid from; none when forever.";
        }
        leaf valid-before {
          type yang:date-and-time;
          description
            "Valid until; none when forever.";
        }
        leaf ca {
          type string;
          description
            "The signing key's fingerprint.";
        }
      }
      leaf certificate-used {
        type boolean;
        description
          "sshd_config names the certificate (HostCertificate).";
      }
    }
    list user {
      cg:struct "user";
      key "name";
      description
        "Those who may sign in.";
      leaf name {
        type string;
        description
          "The user.";
      }
      leaf uid {
        type uint32;
        description
          "Their id.";
      }
      leaf home {
        type string;
        description
          "Their home.";
      }
      leaf shell {
        type string;
        description
          "Their shell.";
      }
      leaf keys-file {
        type string;
        description
          "Their authorized_keys.";
      }
      list key {
        key "fingerprint";
        description
          "Their authorized keys.";
        uses key;
        leaf options {
          type string;
          description
            "The key's options, as written before it.";
        }
      }
    }
    list user-ca-key {
      cg:struct "user-ca-key";
      key "fingerprint";
      description
        "The CA public keys users' certificates are trusted by,
         each a line of TrustedUserCAKeys' file.";
      uses key;
      leaf options {
        type string;
        description
          "The key's options, as written before it.";
      }
    }
    leaf user-cas-text {
      type string;
      description
        "TrustedUserCAKeys' file as it is, when it is small enough
         to be shown.";
    }
    leaf before-kept {
      type boolean;
      description
        "The file before the last change is kept beside
         (sshd_config.arcana-before).";
    }
  }

  container sshd {
    config false;
    description
      "The base system's sshd(8).";
    uses sshd;
    action read {
      description
        "sshd as it is now, the host's or a jail's (one with or
         without a network of its own), which a read of the jails
         leaves out.";
      input {
        leaf jail {
          type string;
          description
            "A running jail's; none, the host's.";
        }
      }
      output {
        uses sshd;
      }
    }
  }
}
