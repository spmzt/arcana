module arcana-agent {
  yang-version 1.1;
  namespace "urn:arcana:yang:arcana-agent";
  prefix arcagent;

  import ietf-netconf-acm {
    prefix nacm;
    reference
      "RFC 8341: Network Configuration Access Control Model";
  }

  import ietf-yang-types {
    prefix yang;
    reference
      "RFC 9911: Common YANG Data Types";
  }

  organization
    "Arcana";
  contact
    "Pouria Mousavizadeh Tehrani <pouria@FreeBSD.org>";
  description
    "The agent itself, arcana-agent: how it is reached (its listeners
     over TCP, SCTP and a unix socket, the sessions open), its own TLS
     files (the host's key and certificate, the CAs it trusts, renewed
     without a restart), and what it does to Arcana: replaced by a
     program sent (checked by its SHA-256 and by running it), built
     from a git repository on the host (cloned afresh, make(1) as an
     unprivileged user, nothing installed), the whole tree built and
     installed to update the console that runs on the host, a
     repository's head and log read over SSH with host keys a person
     confirmed; and the host's configuration as a bundle, to keep or to
     make another host the same with.  The transport, tls, agent-update,
     agent-build, console-update, source-head, source-log, config-export
     and config-apply operations of arcana.yaml converted (Y-3).";

  revision 2026-10-15 {
    description
      "Initial revision.";
  }

  grouping repository {
    description
      "A git repository, as agent-build fetches it.";
    leaf source {
      type string;
      mandatory true;
      description
        "The repository, as git clone takes it.";
    }
    leaf ref {
      type string;
      description
        "The branch or tag; the repository's default if absent.";
    }
    leaf host-keys {
      type string;
      description
        "SSH host keys of the repository's server, as known_hosts
         lines, which a person confirmed.";
    }
    leaf ssh-key {
      type string;
      description
        "A private key on this host for git to show the server.";
    }
  }

  grouping fetched {
    description
      "What a fetch tells of the server.";
    leaf host-keys {
      type string;
      description
        "The server's host keys, as known_hosts lines.";
    }
    leaf-list fingerprint {
      type string;
      description
        "Their fingerprints, as ssh-keygen -l prints them.";
    }
    leaf deploy-key {
      type string;
      description
        "The public key this host shows the server, to be given
         access.";
    }
    leaf refused {
      type string;
      description
        "Why the repository was not fetched, where its server is to be
         confirmed (host-keys) or is to give this host access
         (deploy-key): the action answers with these alone, for a
         person to act on and ask again.";
    }
  }

  grouping cert {
    description
      "A certificate of the agent's own.";
    leaf subject {
      type string;
      description
        "Its subject.";
    }
    leaf issuer {
      type string;
      description
        "Who signed it.";
    }
    leaf not-before {
      type yang:date-and-time;
      description
        "Valid from.";
    }
    leaf not-after {
      type yang:date-and-time;
      description
        "Valid until.";
    }
    leaf sha256 {
      type string;
      description
        "Its fingerprint.";
    }
  }

  grouping bundle {
    description
      "All that makes a host what it is (config-export).";
    leaf host {
      type string;
      description
        "The host's name.";
    }
    leaf agent {
      type string;
      description
        "The agent's version that made it.";
    }
    leaf taken {
      type yang:date-and-time;
      description
        "When.";
    }
    container facts {
      description
        "What the hardware and the system are.";
      leaf arch {
        type string;
        description
          "The machine.";
      }
      leaf release {
        type string;
        description
          "The release.";
      }
      leaf cpu {
        type string;
        description
          "The CPU's model.";
      }
      leaf ncpu {
        type uint32;
        description
          "How many CPUs.";
      }
      leaf memory {
        type uint64;
        units "bytes";
        description
          "The memory.";
      }
      list interface {
        key "name";
        description
          "Each physical interface; a cloned one is configuration.";
        leaf name {
          type string;
          description
            "Its name.";
        }
        leaf driver {
          type string;
          description
            "Its driver.";
        }
        leaf mac {
          type yang:mac-address;
          description
            "Its address.";
        }
      }
      list disk {
        key "name";
        description
          "Each disk.";
        leaf name {
          type string;
          description
            "Its name.";
        }
        leaf size {
          type uint64;
          units "bytes";
          description
            "Its size.";
        }
      }
    }
    list package {
      key "name";
      description
        "The packages installed by hand (pkg query), not the automatic
         ones.";
      leaf name {
        type string;
        description
          "Its name.";
      }
      leaf origin {
        type string;
        description
          "Its origin in the ports tree.";
      }
      leaf version {
        type string;
        description
          "Its version.";
      }
    }
    list file {
      key "path";
      description
        "Each configuration file there is of those Arcana manages.";
      leaf path {
        type string;
        description
          "Where it is.";
      }
      leaf mode {
        type string;
        description
          "Its mode, octal.";
      }
      leaf owner {
        type string;
        description
          "Its owner.";
      }
      leaf group {
        type string;
        description
          "Its group.";
      }
      leaf text {
        type string;
        description
          "Its text; a secret's only when asked for.";
      }
      leaf secret {
        type boolean;
        description
          "It holds a secret, left out unless asked for.";
      }
    }
  }

  container agent {
    description
      "The agent.";
    container transport {
      config false;
      description
        "How the agent is reached.";
      list listener {
        key "uri";
        description
          "Where it listens.";
        leaf uri {
          type string;
          description
            "The address, as a URI.";
        }
        leaf transport {
          type enumeration {
            enum tcp {
              description
                "TCP.";
            }
            enum sctp {
              description
                "SCTP.";
            }
            enum unix {
              description
                "A unix socket.";
            }
          }
          description
            "Which.";
        }
        leaf up {
          type boolean;
          description
            "It listens.";
        }
        leaf why {
          type string;
          description
            "Why not, when it does not.";
        }
        leaf-list address {
          type string;
          description
            "An SCTP listener's: every address it is bound to.";
        }
        leaf also-why {
          type string;
          description
            "Why the other addresses (sctp-also) are not all bound to
             it, where they are not (sctp_bindx(3)).";
        }
      }
      leaf sctp {
        type boolean;
        description
          "The kernel has SCTP: the agent listens on it beside TCP.";
      }
      leaf sctp-also {
        type string;
        description
          "The other addresses every SCTP listener is bound to,
           separated by spaces (arcana_agent_sctp_also); empty: none.";
      }
      leaf seen {
        type uint64;
        description
          "The connections there have been since the agent started.";
      }
      leaf time {
        type yang:date-and-time;
        description
          "When this was read: what since is judged against.";
      }
      list session {
        description
          "The connections open now.";
        leaf transport {
          type string;
          description
            "By which transport.";
        }
        leaf address {
          type string;
          description
            "Who is at the other end.";
        }
        leaf name {
          type string;
          description
            "Their certificate's name.";
        }
        leaf since {
          type yang:date-and-time;
          description
            "Since when.";
        }
        leaf-list local {
          type string;
          description
            "An association's addresses at this end.";
        }
        list path {
          key "address";
          description
            "An association's paths, to each address of the other end,
             as the kernel has them now (SCTP_GET_PEER_ADDR_INFO).";
          leaf address {
            type string;
            description
              "The other end's address.";
          }
          leaf state {
            type enumeration {
              enum active {
                description
                  "In use.";
              }
              enum inactive {
                description
                  "Not reached.";
              }
              enum unconfirmed {
                description
                  "Not yet confirmed by a heartbeat.";
              }
              enum other {
                description
                  "Another state.";
              }
            }
            description
              "Its state.";
          }
          leaf srtt {
            type uint32;
            units "milliseconds";
            description
              "The smoothed round-trip time.";
          }
          leaf rto {
            type uint32;
            units "milliseconds";
            description
              "The retransmission timeout.";
          }
          leaf primary {
            type boolean;
            description
              "The primary path.";
          }
        }
      }
      action retry {
        nacm:default-deny-all;
        description
          "Try SCTP again now.";
      }
      action listen {
        nacm:default-deny-all;
        description
          "The listeners changed: listen there too, then close that one
           (with the SCTP one beside it; not the last the console
           reaches the agent by), the change kept in rc.conf for the
           next start; the other addresses of every SCTP listener set
           anew.";
        input {
          leaf listen {
            type string;
            description
              "A listener to have too, tcp:// or sctp:// and an address
               and port.";
          }
          leaf unlisten {
            type string;
            description
              "A listener to close; the local socket is not one.";
          }
          leaf keep {
            type boolean;
            default "false";
            description
              "With listen and unlisten: kept for the next start too,
               listen in unlisten's place in rc.conf.";
          }
          leaf sctp-also {
            type string;
            description
              "The other addresses every SCTP listener is bound to,
               separated by spaces, in place of those before (empty for
               none), and kept in rc.conf.";
          }
        }
      }
    }
    container tls {
      config false;
      description
        "The host's own TLS files.";
      container certificate {
        description
          "The host's certificate.";
        uses cert;
        list intermediate {
          description
            "The CAs sent after it, its chain, in that order.";
          uses cert;
        }
      }
      list ca {
        description
          "Each CA trusted.";
        uses cert;
      }
      leaf pending {
        type boolean;
        description
          "A key waits for its certificate (csr made).";
      }
      action csr {
        nacm:default-deny-all;
        description
          "A new EC P-256 key made beside the host's (never sent) and
           a certificate request for it.";
        output {
          leaf csr {
            type string;
            description
              "The request, PEM.";
          }
        }
      }
      action install {
        nacm:default-deny-all;
        description
          "A certificate for the waiting key, the CAs to trust, or
           both (one at least); the files before kept beside; read
           again for the connections made from now on.  The asking
           console's own certificate must still be trusted after:
           nothing locks it out.";
        input {
          leaf certificate {
            type string;
            description
              "The certificate, PEM.";
          }
          leaf ca {
            type string;
            description
              "The CAs to trust, PEM.";
          }
          leaf peer {
            type string;
            description
              "The asking console's certificate, PEM.";
          }
        }
      }
    }
    action update {
      nacm:default-deny-all;
      description
        "Replace arcana-agent with the program sent, checked by its
         SHA-256 and by running it with -V; the one before kept beside
         with the suffix .old.";
      input {
        leaf binary {
          type binary;
          mandatory true;
          description
            "The program.";
        }
        leaf sha256 {
          type string;
          mandatory true;
          description
            "Its SHA-256.";
        }
        leaf restart {
          type boolean;
          default "false";
          description
            "Restart the service after the reply.";
        }
        leaf signature {
          type binary;
          description
            "The program's signature by the console's CA key; one sent
             over the local socket is taken without.";
        }
        leaf program-size {
          type uint32 {
            range "1..33554432";
          }
          units "bytes";
          description
            "binary is the program compressed with gzip (RFC 1952),
             which inflates to this many bytes; sha256 and signature
             are the program's, inflated.  Sent to an agent whose
             host's agent feature has gzip-update; one before takes
             the program as it is.";
        }
      }
      output {
        leaf version {
          type string;
          description
            "The version the program in place reports.";
        }
        leaf restarting {
          type boolean;
          description
            "The service is being restarted; the connection drops.";
        }
      }
    }
    action build {
      nacm:default-deny-all;
      description
        "Build arcana-agent from a git repository on this host and
         give the program back; nothing installed.";
      input {
        uses repository;
        leaf compress {
          type boolean;
          default "false";
          description
            "Send the program back compressed with gzip, with
             program-size.";
        }
      }
      output {
        leaf binary {
          type binary;
          description
            "The program built.";
        }
        leaf sha256 {
          type string;
          description
            "Its SHA-256.";
        }
        leaf version {
          type string;
          description
            "Its version.";
        }
        leaf commit {
          type string;
          description
            "The commit built.";
        }
        uses fetched;
        leaf program-size {
          type uint32;
          units "bytes";
          description
            "With compress: binary is the program compressed with
             gzip, which inflates to this many bytes; sha256 is the
             program's.";
        }
      }
    }
    action console-update {
      nacm:default-deny-all;
      description
        "Build the whole tree from a git repository on this host,
         install it and restart the console's service: how a console
         updates itself, through the agent of its host.";
      input {
        uses repository;
      }
      output {
        uses fetched;
        leaf commit {
          type string;
          description
            "The commit installed.";
        }
      }
    }
    action source-head {
      description
        "The commit at the head of a repository's branch, as git
         ls-remote tells it; nothing cloned.";
      input {
        uses repository;
      }
      output {
        leaf commit {
          type string;
          description
            "The commit.";
        }
        uses fetched;
      }
    }
    action source-log {
      description
        "What is new in a repository's branch: its latest commits,
         newest first, and its tags with their messages.";
      input {
        uses repository;
        leaf count {
          type uint32;
          default "100";
          description
            "How many commits at most.";
        }
      }
      output {
        leaf commit {
          type string;
          description
            "The head.";
        }
        list commit-log {
          description
            "Each commit, newest first.";
          leaf hash {
            type string;
            description
              "Its hash.";
          }
          leaf time {
            type yang:date-and-time;
            description
              "When.";
          }
          leaf subject {
            type string;
            description
              "Its subject.";
          }
          leaf body {
            type string;
            description
              "Its body.";
          }
        }
        list tag {
          key "name";
          description
            "Each tag, newest first: the release notes where there are
             any.";
          leaf name {
            type string;
            description
              "The tag.";
          }
          leaf message {
            type string;
            description
              "Its message.";
          }
          leaf time {
            type yang:date-and-time;
            description
              "When it was made.";
          }
        }
        uses fetched;
      }
    }
    action config-export {
      nacm:default-deny-all;
      description
        "The host's configuration as a bundle.";
      input {
        leaf secrets {
          type boolean;
          default "false";
          description
            "With the secrets' texts.";
        }
      }
      output {
        uses bundle;
      }
    }
    action config-apply {
      nacm:default-deny-all;
      description
        "A bundle made this host's configuration: the hardware checked
         first, each file written with the ones before kept, the
         packages missing only told (Arcana installs none itself),
         what the files say taking hold at boot.";
      input {
        container bundle {
          description
            "The bundle, as config-export made it.";
          uses bundle;
        }
        leaf dry-run {
          type boolean;
          default "false";
          description
            "Only the report.";
        }
        leaf anyway {
          type boolean;
          default "false";
          description
            "Even when the hardware differs.";
        }
        leaf hostname {
          type string;
          description
            "This name in rc.conf, instead of the bundle's.";
        }
      }
      output {
        leaf-list mismatch {
          type string;
          description
            "What of the hardware is not here.";
        }
        list file {
          key "path";
          description
            "Each file, and what became of it.";
          leaf path {
            type string;
            description
              "Where.";
          }
          leaf state {
            type enumeration {
              enum same {
                description
                  "As it is.";
              }
              enum changed {
                description
                  "Changed.";
              }
              enum new {
                description
                  "Made.";
              }
              enum withheld {
                description
                  "A secret the bundle does not carry: stays as it
                   is.";
              }
            }
            description
              "What became of it.";
          }
          leaf diff {
            type string;
            description
              "A unified diff, for one changed.";
          }
        }
        leaf-list package {
          type string;
          description
            "Packages the bundle has that this host does not.";
        }
        leaf backup {
          type string;
          description
            "Where the files before are kept.";
        }
        leaf applied {
          type boolean;
          description
            "It was done.";
        }
        leaf reboot {
          type boolean;
          description
            "What the files say takes hold at boot.";
        }
        leaf refused {
          type string;
          description
            "Why nothing was done, the report given still: the
             hardware differs, a file could not be kept or written.";
        }
      }
    }
    container config-files {
      config false;
      description
        "Where a commit writes the host's rc.conf(5) variables and the
         loader's tunables (loader.conf(5)): in Arcana's own files
         (/usr/local/etc/rc.conf.d/arcana, named in rc_conf_files, and
         /boot/loader.conf.d/arcana.conf), or in the system's (the file
         rc(8) or the loader takes the variable from, else /etc/rc.conf
         and /boot/loader.conf).  Changed by switch alone: it moves the
         files.  A variable a commit writes that the admin's files set
         too is a warning first (rc-conf-conflict, loader-conf-
         conflict); a word list (sysrc(8) +=) is then merged, the
         admin's words kept; a value that cannot be merged is refused
         with rc-conf-merge, its rows in pending, until resolve gives
         the value or the warning is accepted for Arcana's.";
      leaf mode {
        type enumeration {
          enum arcana {
            description
              "Arcana's own files, read after the admin's.";
          }
          enum system {
            description
              "The system's files, where the variables are.";
          }
        }
        description
          "The files a commit writes.";
      }
      leaf arcana-at-boot {
        type boolean;
        description
          "Whether rc(8) can read Arcana's own rc.conf file at boot:
           /etc/rc reads rc_conf_files once, before the local
           filesystems are mounted, so the file on one of those
           (/usr/local its own dataset) is missed.  False: mode arcana
           is refused (rc-conf-not-at-boot), commits and the switch to
           it alike; the system's files are the way.";
      }
      leaf rc-file {
        type string;
        description
          "Where a variable no file of the admin's sets goes.";
      }
      leaf loader-file {
        type string;
        description
          "Where a tunable no loader file sets goes.";
      }
      leaf firewall-rules {
        type string;
        description
          "The kept firewall rules' file; its boot script beside it,
           .sh for .rules (firewall_script).";
      }
      list pending {
        key "kind variable";
        description
          "What the last commit refused with rc-conf-merge: a value of
           the admin's that Arcana's would replace, no word list to
           merge.";
        leaf kind {
          type enumeration {
            enum rc {
              description
                "An rc.conf variable.";
            }
            enum loader {
              description
                "A loader tunable.";
            }
          }
          description
            "Which files.";
        }
        leaf variable {
          type string;
          description
            "Its name.";
        }
        leaf file {
          type string;
          description
            "The admin's file that sets it, the last one.";
        }
        leaf line {
          type uint32;
          description
            "Its line there.";
        }
        leaf yours {
          type string;
          description
            "The admin's value.";
        }
        leaf proposed {
          type string;
          description
            "Arcana's.";
        }
        leaf value {
          type string;
          description
            "The value resolve gave, written by the next commit.";
        }
      }
      list ledger {
        key "kind variable";
        description
          "What Arcana changed of a variable the admin's files set, kept
           in /var/db/arcana/config-ledger: release and switch give it
           back from here.";
        leaf kind {
          type enumeration {
            enum rc {
              description
                "An rc.conf variable.";
            }
            enum loader {
              description
                "A loader tunable.";
            }
          }
          description
            "Which files.";
        }
        leaf variable {
          type string;
          description
            "Its name.";
        }
        leaf file {
          type string;
          description
            "Where Arcana wrote it.";
        }
        leaf before {
          type string;
          description
            "The admin's value before; none, it was not set.";
        }
        leaf after {
          type string;
          description
            "What Arcana wrote.";
        }
        leaf arcana {
          type string;
          description
            "Arcana's own value, before any merge.";
        }
      }
      action switch {
        nacm:default-deny-all;
        description
          "The files changed: arcana to system moves each variable of
           Arcana's files into the system's, as the merge rows say;
           system to arcana clones the admin's rc.conf variables and
           loader.conf tunables into Arcana's files, theirs as they
           are.  Every file changed is copied first into a directory
           of /var/db/arcana/config-switch; a failure puts all back.
           Nothing is loaded: rc(8) and the loader read them at the
           next start or boot.";
        input {
          leaf to {
            type enumeration {
              enum arcana {
                description
                  "Arcana's own files.";
              }
              enum system {
                description
                  "The system's files.";
              }
            }
            mandatory true;
            description
              "The mode to switch to.";
          }
          leaf dry-run {
            type boolean;
            default "false";
            description
              "Only the rows: nothing written.";
          }
          list merge {
            key "kind variable";
            description
              "A choice for a variable both Arcana's and the admin's
               files set.";
            leaf kind {
              type enumeration {
                enum rc {
                  description
                    "An rc.conf variable.";
                }
                enum loader {
                  description
                    "A loader tunable.";
                }
              }
              description
                "Which files.";
            }
            leaf variable {
              type string;
              description
                "Its name.";
            }
            leaf choice {
              type enumeration {
                enum additive {
                  description
                    "A word list: the admin's words, then Arcana's not
                     among them, as sysrc(8) += adds them.";
                }
                enum arcana {
                  description
                    "Arcana's value, what boots now.";
                }
                enum yours {
                  description
                    "The admin's value.";
                }
                enum edit {
                  description
                    "The value given.";
                }
                enum remove {
                  description
                    "Neither: the variable unset in every file of the
                     admin's that sets it, Arcana's line not carried
                     over.";
                }
              }
              description
                "What is written.";
            }
            leaf value {
              type string;
              description
                "With edit: the value.";
            }
          }
        }
        output {
          leaf from {
            type string;
            description
              "The mode before.";
          }
          leaf to {
            type string;
            description
              "The mode after, or that would be.";
          }
          leaf done {
            type boolean;
            description
              "Written; false for a dry run or a refusal.";
          }
          list row {
            key "kind variable";
            description
              "Each variable of Arcana's files.";
            leaf kind {
              type string;
              description
                "rc or loader.";
            }
            leaf variable {
              type string;
              description
                "Its name.";
            }
            leaf file {
              type string;
              description
                "The file it ends in.";
            }
            leaf yours {
              type string;
              description
                "The admin's value, an active line's or one commented
                 out as taken by Arcana; none, not set.";
            }
            leaf arcana {
              type string;
              description
                "Arcana's value.";
            }
            leaf list {
              type boolean;
              description
                "A word list, merged additively by default.";
            }
            leaf choice {
              type string;
              description
                "The choice taken; none, one is needed.";
            }
            leaf result {
              type string;
              description
                "The value written, or that would be.";
            }
          }
          leaf-list moved {
            type string;
            description
              "Firewall files moved, from and to.";
          }
          leaf backup {
            type string;
            description
              "The directory the files before are copied into.";
          }
          leaf-list note {
            type string;
            description
              "What else to know.";
          }
        }
      }
      action resolve {
        nacm:default-deny-all;
        description
          "The values the admin merged by hand for pending rows: the
           next commit, accepting rc-conf-merge, writes each where the
           admin's file sets it.";
        input {
          list row {
            key "kind variable";
            description
              "A value for a pending row.";
            leaf kind {
              type enumeration {
                enum rc {
                  description
                    "An rc.conf variable.";
                }
                enum loader {
                  description
                    "A loader tunable.";
                }
              }
              description
                "Which files.";
            }
            leaf variable {
              type string;
              description
                "Its name.";
            }
            leaf value {
              type string;
              mandatory true;
              description
                "The value.";
            }
          }
        }
        output {
          leaf resolved {
            type uint32;
            description
              "Rows given a value.";
          }
        }
      }
    }
  }
}
