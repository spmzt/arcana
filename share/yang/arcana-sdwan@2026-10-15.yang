module arcana-sdwan {
  yang-version 1.1;
  namespace "urn:arcana:yang:arcana-sdwan";
  prefix arcsd;

  import cblink-gen {
    prefix cg;
  }
  import ietf-inet-types {
    prefix inet;
    reference
      "RFC 9911: Common YANG Data Types";
  }
  import ietf-yang-types {
    prefix yang;
    reference
      "RFC 9911: Common YANG Data Types";
  }
  import arcana-firewall {
    prefix arcfw;
  }

  organization
    "Arcana";
  contact
    "Pouria Mousavizadeh Tehrani <pouria@FreeBSD.org>";
  description
    "A FreeBSD host as an SD-WAN edge (MEF 70.2, Mplify 119), what the
     console writes to it and what it tells back: the rules that
     classify what comes in at the UNIs and steer it (an ipfw set of
     their own, tables, dummynet and NAT objects); the policy tables'
     candidates in the console's order, the first whose far end the
     probes do not say is down chosen; the BIRD, dnsmasq, unbound (MEF
     138's DNF and PDNS), Squid (MEF 138's URLF, MBSF and MD+R, with a
     CA of its own where TLS is opened) and Suricata (the ids
     criterion) instances of the services, one each in its FIB
     (setfib), and the Security section's Squid and Suricata (named
     sec-), as the console writes them; the rules, steering and BIRD of
     each edge that is a vnet jail under jail; and as state what each
     is doing, the security policies' record (ipfw's logdst rtsock),
     the IPsec keys of the tunnels (sdwan-key-*.pem) and the faults of
     the day (Mplify 119 §11.3).  Written by EDIT and a commit: what
     changed of an edge is applied as the operations did, the rules
     and the steering each swapped whole.  The sdwan, sdwan-rules,
     sdwan-steer, sdwan-bird, sdwan-dhcp, sdwan-dns, sdwan-proxy and
     sdwan-ids operations of arcana.yaml converted (Y-3) and retired;
     the probes are arcana-probe's.";

  revision 2026-10-15 {
    description
      "Initial revision.";
  }

  typedef far-state {
    type enumeration {
      enum up {
        description
          "Up.";
      }
      enum down {
        description
          "Down.";
      }
      enum unknown {
        description
          "Not yet known.";
      }
      enum not-probed {
        description
          "No probe watches it.";
      }
    }
    description
      "A tunnel's far end, as the probes see it.";
  }

  grouping candidate-state {
    description
      "A candidate of the steering, as it is.";
    leaf id {
      type string;
      description
        "The tunnel.";
    }
    leaf via {
      type inet:ip-address-no-zone;
      description
        "Its address.";
    }
    leaf state {
      type far-state;
      description
        "As the probes see it.";
    }
  }

  grouping edge-state {
    description
      "An edge's rules as the kernel has them, and its steering.";
    container rules {
      cg:struct "rules";
      description
        "The rules as the kernel has them.";
      leaf set {
        type uint8;
        description
          "Their set.";
      }
      leaf rules {
        type uint32;
        description
          "How many.";
      }
      leaf objects {
        type uint32;
        description
          "How many objects.";
      }
      list table {
        key "name";
        description
          "The tables, and what each holds.";
        leaf name {
          type string;
          description
            "The table.";
        }
        leaf count {
          type uint32;
          description
            "Its entries.";
        }
      }
      list counter {
        key "rule";
        description
          "Each rule's counters.";
        leaf rule {
          type arcfw:rule-number;
          description
            "The rule.";
        }
        leaf packets {
          type uint64;
          description
            "Packets it matched.";
        }
        leaf octets {
          type uint64;
          description
            "Their bytes.";
        }
        leaf text {
          type string;
          description
            "Its words.";
        }
      }
    }
    leaf steered {
      type boolean;
      description
        "The policy tables are filled as the steer says.";
    }
    list steer {
      cg:struct "steer";
      key "table prefix";
      description
        "What the policy tables hold now.";
      leaf table {
        type string;
        description
          "The table.";
      }
      leaf prefix {
        type string;
        description
          "The prefix.";
      }
      leaf chosen {
        type int32;
        description
          "Which candidate is in the table, by its place; -1
           none.";
      }
      list candidate {
        key "id";
        ordered-by user;
        description
          "The candidates, with what the probes say of each.";
        uses candidate-state;
        leaf bfd {
          type far-state;
          description
            "As BFD sees its address, where a session watches it.";
        }
      }
    }
    list route {
      cg:struct "steered-route";
      description
        "The breakout's routes steered: each a destination of a FIB
         and its candidates, the first not down in the table.";
      leaf fib {
        type uint16;
        description
          "The FIB.";
      }
      leaf destination {
        type string;
        description
          "The destination.";
      }
      leaf chosen {
        type int32;
        description
          "Which candidate is the route, by its place; -1 none.";
      }
      list candidate {
        key "id";
        ordered-by user;
        description
          "The candidates.";
        uses candidate-state;
      }
    }
  }

  grouping instance {
    description
      "A service's instance of a program, in its FIB.";
    leaf name {
      type string;
      description
        "The service's name.";
    }
    leaf fib {
      type uint16;
      description
        "The FIB it runs in (setfib).";
    }
    leaf conf {
      type string;
      config false;
      description
        "The program's configuration text, as the agent rendered it
         from spec.";
    }
    leaf host {
      type string;
      description
        "The host's name, for the files' comments.";
    }
    leaf spec {
      type string;
      description
        "The form the agent renders the program's configuration from:
         a JSON object (RFC 8259), the console's SD-WAN document's or
         the Security section's, until the module says the forms
         (PLAN-SDN-YANG 4.5.5).";
    }
  }

  grouping edge-config {
    description
      "What the console writes to an edge, the host's or a vnet
       jail's: its rules, its steering and its BIRD instances.";
    container rules {
      cg:struct "rules-config";
      description
        "The classification and steering rules, as the console
         compiles them: kept for the next start; with none, the set
         is emptied.";
      leaf set {
        type uint8 {
          range "2..31";
        }
        description
          "The ipfw set they live in, emptied and filled while
           disabled.";
      }
      list table {
        key "name";
        description
          "The lookup tables the rules name.";
        leaf name {
          type string;
          description
            "The table.";
        }
        leaf valtype {
          type enumeration {
            enum skipto {
              description
                "A rule number.";
            }
            enum ipv4 {
              description
                "An IPv4 next hop.";
            }
            enum ipv6 {
              description
                "An IPv6 next hop.";
            }
            enum legacy {
              description
                "A number.";
            }
          }
          description
            "What its values are.";
        }
        list entry {
          key "prefix";
          description
            "Its entries.";
          leaf prefix {
            type string;
            description
              "The key.";
          }
          leaf value {
            type string;
            description
              "The value.";
          }
        }
      }
      leaf-list object {
        type string;
        ordered-by user;
        description
          "dummynet pipes, queues and schedulers, and NAT instances
           the rules name, each as ipfw takes it (pipe N config ...),
           made before the rules, deleted with them.";
      }
      list rule {
        key "index";
        description
          "The rules, in their order: ipfw lets rules share a
           number.";
        leaf index {
          type uint32;
          description
            "Its place, from 0.";
        }
        leaf number {
          type arcfw:rule-number;
          mandatory true;
          description
            "Its number.";
        }
        leaf text {
          type string;
          description
            "Its words.";
        }
      }
    }
    container steer {
      cg:struct "steer-config";
      description
        "What the policy tables hold, kept for the next start; made
         again when a probe's state changes.";
      list entry {
        key "table prefix";
        description
          "A prefix's candidates, in the console's order.";
        leaf table {
          type string;
          description
            "The policy table.";
        }
        leaf prefix {
          type string;
          description
            "The prefix.";
        }
        list candidate {
          key "id";
          ordered-by user;
          description
            "The tunnels it may go by, best first.";
          leaf id {
            type string;
            description
              "The tunnel, as the probes know it.";
          }
          leaf via {
            type inet:ip-address-no-zone;
            description
              "The address it goes by.";
          }
        }
      }
      list route {
        key "fib destination";
        description
          "The breakout's routes steered: a destination of a FIB and
           the gateways it may go by, in the console's order, the
           first whose far end the probes do not say is down the
           route.";
        leaf fib {
          type uint16;
          description
            "The FIB.";
        }
        leaf destination {
          type string;
          description
            "The destination.";
        }
        list candidate {
          key "id";
          ordered-by user;
          description
            "The gateways, best first.";
          leaf id {
            type string;
            description
              "The probe target that watches it.";
          }
          leaf via {
            type inet:ip-address-no-zone;
            description
              "The gateway.";
          }
        }
      }
    }
    list bird-instance {
      cg:struct "bird-instance";
      key "name";
      description
        "The BIRD instances of the services, and of the UCS End
         Points that route with the underlay: each file parsed by
         bird -p before it is the instance's; one running told to
         read it again, one not yet started; those not named any more
         stopped.";
      uses instance;
    }
  }

  grouping running {
    description
      "An instance as it runs.";
    leaf name {
      type string;
      description
        "The service.";
    }
    leaf fib {
      type uint16;
      description
        "Its FIB.";
    }
    leaf running {
      type boolean;
      description
        "Its process is there.";
    }
  }

  grouping file {
    description
      "A file of an instance's.";
    leaf path {
      type string;
      description
        "Where.";
    }
    leaf size {
      type uint64;
      units "bytes";
      description
        "How long.";
    }
    leaf at {
      type yang:date-and-time;
      description
        "When last written.";
    }
  }

  container sdwan {
    description
      "The edge.";
    uses edge-config;
    list dhcp-instance {
      key "name";
      description
        "The dnsmasq instances: each checked by dnsmasq --test before
         it is the instance's, one running started again on it.";
      uses instance;
    }
    list dns-instance {
      key "name";
      description
        "The unbound instances: each checked by
         local-unbound-checkconf, one running started again on it.";
      uses instance;
    }
    list proxy-instance {
      key "name";
      description
        "The Squid instances, SD-WAN's and the Security section's
         (sec-): each checked by squid -k parse, one running told to
         reconfigure.";
      uses instance;
      leaf mode {
        type enumeration {
          enum sni {
            description
              "The TLS names looked at, nothing opened.";
          }
          enum inspect {
            description
              "TLS opened, with a CA of the instance's own.";
          }
        }
        description
          "How TLS is treated.";
      }
      list named-list {
        key "name";
        description
          "The files a zone's URLF names, by name.";
        leaf name {
          type string;
          description
            "The list.";
        }
        leaf text {
          type string;
          description
            "Its text.";
        }
      }
      leaf stopped {
        type boolean;
        description
          "Stopped by the admin: kept, not run, nor its c-icap.";
      }
    }
    list ids-instance {
      key "name";
      description
        "The Suricata instances, SD-WAN's and the Security section's
         (sec-): each checked by suricata -T before it runs, one whose
         files changed started again.";
      leaf name {
        type string;
        description
          "The service.";
      }
      leaf-list interface {
        type string;
        ordered-by user;
        description
          "The UNIs it watches.";
      }
      leaf conf {
        type string;
        description
          "Suricata's YAML whole, with @LOGDIR@, @RULES@, @PID@ and
           @THRESHOLD@ for what the agent places; or spec instead.";
      }
      leaf rules {
        type string;
        description
          "The service's own rules, one a line.";
      }
      leaf divert {
        type inet:port-number;
        description
          "For one that prevents: the divert port it runs on.";
      }
      leaf host {
        type string;
        description
          "The host's name, for the YAML's comment.";
      }
      leaf spec {
        type string;
        description
          "Its settings, a JSON object (RFC 8259), which the agent
           renders into Suricata's YAML: the console's form, or for an
           SD-WAN service flavor sdwan.";
      }
      leaf capture {
        type enumeration {
          enum pcap {
            description
              "By libpcap.";
          }
          enum netmap {
            description
              "By netmap(4).";
          }
        }
        description
          "How it takes the packets, where it does not prevent.";
      }
      leaf offload {
        type boolean;
        description
          "false: its interfaces' offloading turned off as it starts.";
      }
      list lua {
        key "name";
        description
          "Its Lua scripts.";
        leaf name {
          type string;
          description
            "NAME.lua.";
        }
        leaf text {
          type string;
          description
            "The script.";
        }
      }
      leaf-list plugin {
        type string;
        ordered-by user;
        description
          "The plugins it loads, .so files under /usr/local/lib.";
      }
      leaf stopped {
        type boolean;
        description
          "Stopped by the admin: kept, not run.";
      }
      leaf thresholds {
        type string;
        description
          "Its threshold.config lines.";
      }
    }
    list jail {
      key "name";
      description
        "Each edge that is a vnet jail on this host: its rules,
         steering and BIRD, run in it.";
      leaf name {
        type string;
        description
          "The jail.";
      }
      uses edge-config;
    }
    action apply {
      description
        "A part of an edge set again as running has it, as its
         operation was when sent the same again: what of it is not
         running started (one the admin stopped left so), what runs
         left be.  An edit that changes nothing sets nothing; this
         does.";
      input {
        leaf part {
          type enumeration {
            enum rules {
              description
                "The rules.";
            }
            enum steer {
              description
                "The steering.";
            }
            enum bird {
              description
                "The BIRD instances.";
            }
            enum dhcp {
              description
                "The dnsmasq instances.";
            }
            enum dns {
              description
                "The unbound instances.";
            }
            enum proxy {
              description
                "The Squid instances.";
            }
            enum ids {
              description
                "The Suricata instances.";
            }
          }
          mandatory true;
          description
            "Which.";
        }
        leaf jail {
          type string;
          description
            "The edge that is this vnet jail; none, the host's.";
        }
        leaf security {
          type boolean;
          default "false";
          description
            "For the proxies and the IDS: the Security section's
             (sec-), not SD-WAN's.";
        }
      }
    }
    container state {
      config false;
      description
        "What the edge is doing.";
      uses edge-state;
      list edge {
        key "jail";
        description
          "Each edge that is a vnet jail on this host: its rules and
           steering, its own ipfw's.";
        leaf jail {
          type string;
          description
            "The jail.";
        }
        uses edge-state;
        leaf error {
          type string;
          description
            "Why its ipfw could not be read.";
        }
      }
      list bird {
        description
          "Each BIRD instance, and its protocols.";
        uses running;
        leaf jail {
          type string;
          description
            "The edge that is a vnet jail it runs in; none, the
             host's.";
        }
        list protocol {
          key "name";
          description
            "Its protocols.";
          leaf name {
            type string;
            description
              "The protocol.";
          }
          leaf proto {
            type string;
            description
              "Its kind.";
          }
          leaf state {
            type string;
            description
              "up, down ...";
          }
          leaf info {
            type string;
            description
              "What birdc says beside.";
          }
        }
        list bfd {
          description
            "Its BFD sessions.";
          leaf address {
            type string;
            description
              "The far end.";
          }
          leaf interface {
            type string;
            description
              "The interface.";
          }
          leaf state {
            type enumeration {
              enum up {
                description
                  "Up.";
              }
              enum down {
                description
                  "Down.";
              }
              enum unknown {
                description
                  "Not known.";
              }
            }
            description
              "The session's state.";
          }
          leaf since {
            type string;
            description
              "Since when.";
          }
        }
      }
      list dhcp {
        key "name";
        description
          "Each dnsmasq instance, and the leases it gave.";
        uses running;
        list lease {
          description
            "A lease.";
          leaf expires {
            type yang:date-and-time;
            description
              "When it ends.";
          }
          leaf id {
            type string;
            description
              "The client's identifier (its MAC).";
          }
          leaf address {
            type inet:ip-address-no-zone;
            description
              "The address given.";
          }
          leaf hostname {
            type string;
            description
              "The client's name.";
          }
        }
      }
      list dns {
        key "name";
        description
          "Each unbound instance.";
        uses running;
        leaf tls-cert {
          type string;
          description
            "Its certificate, PEM, where it serves DNS over TLS.";
        }
      }
      list proxy {
        key "name";
        description
          "Each Squid instance.";
        uses running;
        leaf mode {
          type string;
          description
            "sni or inspect.";
        }
        leaf icap {
          type boolean;
          description
            "Its c-icap runs.";
        }
        leaf ca {
          type string;
          description
            "Its CA's certificate, PEM, for the clients to trust
             where TLS is opened.";
        }
      }
      container clamav {
        description
          "ClamAV's signatures, for the proxies that scan for
           malware, as freshclam left them.";
        list database {
          key "name";
          description
            "Each database there.";
          leaf name {
            type string;
            description
              "main, daily or bytecode.";
          }
          leaf file {
            type string;
            description
              "Its file.";
          }
          leaf built {
            type string;
            description
              "When it was built, as its head says.";
          }
          leaf version {
            type int64;
            description
              "Its version.";
          }
          leaf signatures {
            type int64;
            description
              "Its signatures.";
          }
        }
        leaf freshclam {
          type boolean;
          description
            "freshclam runs.";
        }
        leaf conf {
          type boolean;
          description
            "freshclam's configuration is there, and not the port's
             sample.";
        }
        leaf-list mirror {
          type string;
          ordered-by user;
          description
            "Its DatabaseMirror lines.";
        }
        leaf-list log {
          type string;
          ordered-by user;
          description
            "The last lines of its log.";
        }
      }
      list ids {
        key "name";
        description
          "Each Suricata instance, and its latest alerts.";
        leaf name {
          type string;
          description
            "The service.";
        }
        leaf-list interface {
          type string;
          ordered-by user;
          description
            "The UNIs it watches.";
        }
        leaf mode {
          type enumeration {
            enum detect {
              description
                "Watches by libpcap.";
            }
            enum prevent {
              description
                "On a divert port: nothing passes while it is not
                 running.";
            }
          }
          description
            "How it runs.";
        }
        leaf divert {
          type inet:port-number;
          description
            "Its divert port, when it prevents.";
        }
        leaf running {
          type boolean;
          description
            "Its process is there.";
        }
        leaf alerts-seen {
          type uint64;
          description
            "Alerts read in all.";
        }
        list alert {
          description
            "The latest alerts, newest first.";
          leaf time {
            type string;
            description
              "When, as Suricata wrote it.";
          }
          leaf name {
            type string;
            description
              "The signature.";
          }
          leaf source {
            type string;
            description
              "Where from.";
          }
          leaf source-port {
            type inet:port-number;
            description
              "Its port.";
          }
          leaf destination {
            type string;
            description
              "Where to.";
          }
          leaf destination-port {
            type inet:port-number;
            description
              "Its port.";
          }
          leaf proto {
            type string;
            description
              "The protocol.";
          }
          leaf interface {
            type string;
            description
              "Where it came in.";
          }
          leaf signature-id {
            type int64;
            description
              "The signature's id.";
          }
          leaf rev {
            type int64;
            description
              "Its revision.";
          }
          leaf category {
            type string;
            description
              "Its category.";
          }
          leaf severity {
            type int64;
            description
              "Its severity.";
          }
          leaf action {
            type string;
            description
              "allowed or blocked.";
          }
        }
        leaf stopped {
          type boolean;
          description
            "Stopped by the admin.";
        }
        container stats {
          description
            "Its counters as Suricata wrote them, the oldest first.";
          leaf-list field {
            type string;
            ordered-by user;
            description
              "What each value of a row is.";
          }
          list series {
            description
              "A row.";
            leaf-list value {
              type int64;
              ordered-by user;
              description
                "Its values, as field names them.";
            }
          }
          leaf flows {
            type string;
            description
              "The flows by application layer protocol, JSON as the
               agent read them.";
          }
        }
        leaf capture {
          type enumeration {
            enum pcap {
              description
                "libpcap.";
            }
            enum divert {
              description
                "divert(4).";
            }
            enum netmap {
              description
                "netmap(4).";
            }
          }
          description
            "How it takes the packets.";
        }
        list pcap {
          key "path";
          description
            "The packets it logged.";
          uses file;
          leaf from {
            type int64;
            description
              "The time in its name, where it has one.";
          }
        }
        list replay-capture {
          key "path";
          description
            "The captures that came for its replay.";
          uses file;
        }
        leaf replay {
          type string;
          description
            "The last capture replayed through it, JSON as the agent
             wrote it.";
        }
        list offload {
          key "interface";
          description
            "Each interface's offloading still on.";
          leaf interface {
            type string;
            description
              "The interface.";
          }
          leaf-list capability {
            type string;
            ordered-by user;
            description
              "rxcsum, txcsum, tso4 ... as ifconfig(8) names them.";
          }
        }
      }
      container ids-build {
        description
          "What the host's Suricata is built with (--build-info).";
        leaf version {
          type string;
          description
            "Its version.";
        }
        leaf lua {
          type boolean;
          description
            "HAVE_LUA.";
        }
        leaf profiling {
          type boolean;
          description
            "Profiling.";
        }
        leaf profiling-rules {
          type boolean;
          description
            "Rule profiling.";
        }
        leaf profiling-locks {
          type boolean;
          description
            "Lock profiling.";
        }
        leaf hyperscan {
          type boolean;
          description
            "Hyperscan.";
        }
        leaf netmap {
          type boolean;
          description
            "netmap(4).";
        }
        leaf ipfw {
          type boolean;
          description
            "IPFW, divert(4).";
        }
        leaf plugins {
          type boolean;
          description
            "Plugins.";
        }
      }
      container ids-host {
        description
          "The host's CPUs and memory domains, for the instances'
           threads.";
        leaf ncpu {
          type uint32;
          description
            "hw.ncpu.";
        }
        leaf ndomains {
          type uint32;
          description
            "vm.ndomains.";
        }
        list irq {
          key "irq";
          description
            "The interrupts of the instances' interfaces.";
          leaf irq {
            type uint32;
            description
              "Its number.";
          }
          leaf name {
            type string;
            description
              "As hw.intrnames has it.";
          }
          leaf cpus {
            type string;
            description
              "The CPUs it may run on, as cpuset(1) lists them.";
          }
        }
      }
      container ids-ruleset {
        description
          "The ruleset suricata-update fetched, where it has.";
        uses file;
      }
      container record {
        description
          "The security policies' record: what the rules that log to
           the routing socket saw.";
        leaf count {
          type uint64;
          description
            "The day's count.";
        }
        leaf sequence {
          type uint64;
          description
            "The latest number.";
        }
        leaf untold {
          type uint64;
          description
            "Those dropped before they were told.";
        }
        list last {
          description
            "The latest, newest first.";
          leaf time {
            type yang:date-and-time;
            description
              "When.";
          }
          leaf sequence {
            type uint64;
            description
              "Its number.";
          }
          leaf rule {
            type uint32;
            description
              "The rule.";
          }
          leaf action {
            type string;
            description
              "What it did.";
          }
          leaf source {
            type string;
            description
              "Where from.";
          }
          leaf destination {
            type string;
            description
              "Where to.";
          }
          leaf interface {
            type string;
            description
              "On which interface.";
          }
          leaf comment {
            type string;
            description
              "The rule's comment: the policy.";
          }
        }
      }
      list key {
        key "interface";
        description
          "The IPsec keys of the tunnels, by interface
           (sdwan-key-<if>.pem): public parts and times only.";
        leaf interface {
          type string;
          description
            "The tunnel's interface.";
        }
        leaf public {
          type string;
          description
            "Its public key.";
        }
        leaf next {
          type string;
          description
            "The next key's public part, when one waits.";
        }
        leaf keyed-at {
          type yang:date-and-time;
          description
            "When the key was made.";
        }
        leaf lifetime {
          type uint32;
          units "seconds";
          description
            "How long it lives.";
        }
        leaf spi-in {
          type uint32;
          description
            "The inbound SPI.";
        }
        leaf spi-out {
          type uint32;
          description
            "The outbound SPI.";
        }
        leaf next-spi-in {
          type uint32;
          description
            "The next key's inbound SPI.";
        }
        leaf pending {
          type boolean;
          description
            "A rekey waits.";
        }
      }
      list fault {
        description
          "The faults of the day (Mplify 119 Table 5), newest
           first.";
        leaf time {
          type yang:date-and-time;
          description
            "When seen.";
        }
        leaf type {
          type string;
          description
            "Its type.";
        }
        leaf severity {
          type string;
          description
            "Critical, Major, Minor, Warning.";
        }
        leaf was {
          type string;
          description
            "The severity before, when it changed.";
        }
        leaf object {
          type string;
          description
            "What it is about.";
        }
        leaf by {
          type string;
          description
            "What found it.";
        }
        leaf description {
          type string;
          description
            "In words.";
        }
        leaf cleared {
          type boolean;
          description
            "Gone.";
        }
        leaf cleared-at {
          type yang:date-and-time;
          description
            "When it went.";
        }
        leaf compressed {
          type boolean;
          description
            "Others like it before were folded into it.";
        }
      }
    }
  }
}
