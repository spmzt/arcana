module arcana-console {
  yang-version 1.1;
  namespace "urn:arcana:yang:arcana-console";
  prefix arcc;

  import ietf-yang-types {
    prefix yang;
    reference
      "RFC 9911: Common YANG Data Types";
  }
  import ietf-inet-types {
    prefix inet;
    reference
      "RFC 9911: Common YANG Data Types";
  }

  organization
    "Arcana";
  contact
    "Pouria Mousavizadeh Tehrani <pouria@FreeBSD.org>";
  description
    "The console's own configuration and state, served by its RESTCONF
     from the files it keeps in its data directory (settings.json,
     tokens.json, users.json, workflows.json, runs.json and the
     others): its settings, API tokens, users, roles and groups (its
     RBAC), the enrolment of hosts by token, the workflows and their
     runs, the fleet's templates, interface labels, prefix lists,
     threat feeds and snapshot transfers, and the Web Push
     subscriptions.  No agent serves it.

     Who may: the console's owners, but for the workflows, runs,
     templates, threat feeds and transfers, which its operators may
     too, and the labels, prefix lists and Web Push subscriptions,
     which every user reads (a label set by whom may change its host,
     a prefix list changed by operators, a subscription its user's
     alone).  A secret (a token's value, a bot's token, a directory's
     password, a subscription's keys) is never read: it is set, and
     whether it is set is what is said.  A value made by the console
     (a token, an invitation, an enrolment token) is the output of an
     action, said once.  Times are the console's clock, UTC.";

  revision 2026-11-05 {
    description
      "Initial revision.";
  }

  typedef severity {
    type enumeration {
      enum Critical;
      enum Major;
      enum Minor;
      enum Warning;
      enum none;
    }
    description
      "The least severity of a fault told, and its clearing; none for
       none.";
  }

  typedef which {
    type enumeration {
      enum failed;
      enum all;
      enum none;
    }
    description
      "Which jobs or runs are told: the failed ones, all, or none.";
  }

  typedef host-id {
    type string {
      pattern '[0-9a-f]{8}';
    }
    description
      "A host's id, as arcana-fleet's host list has it.";
  }

  typedef name {
    type string {
      length "1..64";
      pattern '[A-Za-z0-9_.@-]+';
    }
    description
      "A user's, a role's, a group's or a tenant's name.";
  }

  typedef notify-via {
    type enumeration {
      enum mail;
      enum telegram;
      enum all;
    }
    description
      "How a step tells: by mail, Telegram, or both.";
  }

  /* The settings */

  container settings {
    description
      "The settings that change while the console runs: settings.json,
       over web.conf's.  A leaf left out is web.conf's again; a leaf
       read is the value in force.  The secrets (telegram-token,
       ldap-bind-password) are never read: left out of a change, they
       stay; set to the empty string, they are cleared.";
    leaf rp-name {
      type string {
        length "1..64";
      }
      description
        "The name a security key or passkey shows for this console.";
    }
    leaf update-check {
      type boolean;
      description
        "Ask the release feed every few hours whether a newer version
         is out.";
    }
    leaf update-url {
      type string;
      description
        "The release feed: a URL in the shape of GitHub's
         releases/latest.";
    }
    leaf agent-binary {
      type string;
      description
        "The arcana-agent sent to hosts when they are updated, until a
         host has built one from agent-source.";
    }
    leaf agent-source {
      type string;
      description
        "A git repository with the Arcana tree the hosts build the
         agent from; empty for none.  Whoever sets it decides what runs
         as root on every host.";
    }
    leaf agent-ref {
      type string;
      description
        "The branch or tag built; empty for the repository's own.";
    }
    leaf agent-ssh-key {
      type string;
      description
        "The path of a private key on the build host for a repository
         reached over SSH; empty for one the host makes.";
    }
    leaf session-idle {
      type uint16 {
        range "5..1440";
      }
      units "minutes";
      description
        "A sign-in not used for this long ends.";
    }
    leaf session-max {
      type uint16 {
        range "1..720";
      }
      units "hours";
      description
        "A sign-in lasts at most this long, however much it is used.";
    }
    leaf hsts-days {
      type uint16 {
        range "0..730";
      }
      units "days";
      description
        "How long Strict-Transport-Security keeps a browser to HTTPS;
         0, none sent.";
    }
    leaf mail-to {
      type string;
      description
        "The addresses mailed by sendmail(8), by commas; empty for no
         mail.";
    }
    leaf mail-from {
      type string;
      description
        "The sender's address; empty for arcana@ the host's name.";
    }
    leaf mail-faults {
      type severity;
      description
        "The faults mailed.";
    }
    leaf mail-jobs {
      type which;
      description
        "The jobs mailed.";
    }
    leaf mail-runs {
      type which;
      description
        "The workflow runs mailed.";
    }
    leaf mail-limits {
      type boolean;
      description
        "A host's usage crossing a limit, and coming back under,
         mailed.";
    }
    leaf telegram-chats {
      type string;
      description
        "The chats the bot writes to, by spaces: ids or @channel
         names.";
    }
    leaf telegram-token {
      type string;
      description
        "The bot's token, as BotFather gave it: write-only.";
    }
    leaf telegram-token-set {
      type boolean;
      config false;
      description
        "Whether telegram-token is set.";
    }
    leaf telegram-via {
      type string;
      description
        "The host whose agent sends to api.telegram.org, by name or
         id; empty for the agent beside the console.";
    }
    leaf telegram-faults {
      type severity;
      description
        "The faults sent to Telegram.";
    }
    leaf telegram-jobs {
      type which;
      description
        "The jobs sent to Telegram.";
    }
    leaf telegram-runs {
      type which;
      description
        "The workflow runs sent to Telegram.";
    }
    leaf telegram-limits {
      type boolean;
      description
        "A host's usage crossing a limit sent to Telegram.";
    }
    leaf mail-sen {
      type string;
      description
        "Where MEF 138's Security Event Notifications are mailed, by
         commas.";
    }
    leaf mail-san {
      type string;
      description
        "Where MEF 138's Security Admin Notifications are mailed, by
         commas.";
    }
    leaf telegram-sen {
      type string;
      description
        "The chats the Security Event Notifications go to.";
    }
    leaf telegram-san {
      type string;
      description
        "The chats the Security Admin Notifications go to.";
    }
    leaf feeds-allow-private {
      type string;
      description
        "The prefixes a threat feed may be fetched from although they
         are not the internet's, by spaces.";
    }
    leaf ldap-url {
      type string;
      description
        "The directory users sign in by: ldaps:// or ldap:// (StartTLS
         required); empty for none.";
    }
    leaf ldap-ca {
      type string;
      description
        "A PEM file holding the directory's CA; empty for the
         system's.";
    }
    leaf ldap-base {
      type string;
      description
        "Where users are looked up, the subtree under it.";
    }
    leaf ldap-user-attr {
      type string;
      description
        "The attribute that is the user name.";
    }
    leaf ldap-group {
      type string;
      description
        "A group whose members alone may sign in; empty for anyone
         the base holds.";
    }
    leaf ldap-bind-dn {
      type string;
      description
        "The DN the console binds as to look users up; empty for
         anonymously.";
    }
    leaf ldap-bind-password {
      type string;
      description
        "The reader's password: write-only.";
    }
    leaf ldap-bind-password-set {
      type boolean;
      config false;
      description
        "Whether ldap-bind-password is set.";
    }
    leaf safe-wait {
      type uint16 {
        range "10..3600";
      }
      units "seconds";
      description
        "How long a change made in safe mode waits to hear from the
         console before the host undoes it; left out, each agent's
         own.";
    }
    leaf notify-cooldown {
      type uint16 {
        range "0..1440";
      }
      units "minutes";
      description
        "Of one thing on one host (a figure and its limit, a fault
         and what it is of), the first change is told at once and
         those after it within so long held; at its end one line
         says what happened, unless it ended as it was last told.
         Each way alike; 0, every change told.  30 unless set.";
    }
    list source {
      key "name";
      config false;
      description
        "Where each setting comes from.";
      leaf name {
        type string;
        description
          "The setting.";
      }
      leaf overridden {
        type boolean;
        description
          "Set here, over web.conf's.";
      }
      leaf web-conf {
        type string;
        description
          "What web.conf says, but of a secret.";
      }
      leaf label {
        type string;
        description
          "Its name in the page's form.";
      }
      leaf help {
        type string;
        description
          "What the page's form says of it.";
      }
    }
    container fixed {
      config false;
      description
        "What web.conf alone sets, read once at the start.";
      leaf relying-party {
        type string;
        description
          "The WebAuthn relying party every key is bound to.";
      }
      leaf origin {
        type string;
        description
          "The console's origin.";
      }
      leaf data-directory {
        type string;
        description
          "Where the console keeps its files.";
      }
      leaf cookie-secure {
        type boolean;
        description
          "The session cookie over HTTPS only.";
      }
      leaf agent-certificates {
        type string;
        description
          "The certificates for the agents: the console's own CA, or
           web.conf's file.";
      }
    }
    action mail-test {
      description
        "A mail to say mail goes out, by sendmail(8) on the console's
         host, to whom the settings name.";
      output {
        leaf to {
          type string;
          description
            "Whom it was sent to.";
        }
      }
    }
    action telegram-test {
      description
        "A message to say Telegram reaches the chats, sent by the host
         the settings name.";
      output {
        leaf to {
          type string;
          description
            "The chats it was sent to.";
        }
      }
    }
  }

  /* API tokens */

  container tokens {
    description
      "API tokens, for a program to use the console without a
       passkey, each kept as its SHA-256 alone.  Made by the create
       action, its value said once; removed by deleting its entry; its
       name and kind are not changed.";
    list token {
      key "id";
      description
        "A token.";
      leaf id {
        type string {
          pattern '[0-9a-f]{16}';
        }
        description
          "The first eight bytes of its hash, in hex.";
      }
      leaf name {
        type string {
          length "1..64";
        }
        mandatory true;
        description
          "What it is for.";
      }
      leaf kind {
        type enumeration {
          enum read {
            description
              "It reads.";
          }
          enum write {
            description
              "It reads and changes.";
          }
        }
        default "read";
        description
          "What it may.";
      }
      leaf created {
        type yang:date-and-time;
        config false;
        description
          "When it was made.";
      }
      leaf last-used {
        type yang:date-and-time;
        config false;
        description
          "When it was last used.";
      }
    }
    action create {
      description
        "A new token; its value is said here alone.";
      input {
        leaf name {
          type string {
            length "1..64";
          }
          mandatory true;
          description
            "What it is for.";
        }
        leaf kind {
          type enumeration {
            enum read;
            enum write;
          }
          default "read";
          description
            "What it may.";
        }
      }
      output {
        leaf id {
          type string;
          description
            "Its id.";
        }
        leaf token {
          type string;
          description
            "Its value, sent as Authorization: Bearer.";
        }
      }
    }
  }

  /* Who may: users, roles and groups */

  container users {
    description
      "The console's users.  A user has roles, its own and its
       groups'; may belong to a tenant, which then limits it to that
       tenant's hosts.  The console keeps an owner.";
    list user {
      key "name";
      description
        "A user.";
      leaf name {
        type name;
        description
          "Its name.";
      }
      leaf tenant {
        type name;
        description
          "Its tenant; none, every host.";
      }
      leaf-list role {
        type leafref {
          path "/arcc:roles/arcc:role/arcc:name";
        }
        description
          "Its roles.";
      }
      leaf-list group {
        type leafref {
          path "/arcc:groups/arcc:group/arcc:name";
        }
        description
          "The groups it is in.";
      }
      leaf created {
        type yang:date-and-time;
        config false;
        description
          "When it was made.";
      }
      leaf console-role {
        type enumeration {
          enum owner;
          enum operator;
          enum member;
          enum none;
        }
        config false;
        description
          "The most its roles allow on the console.";
      }
      leaf keys {
        type uint32;
        config false;
        description
          "Its sign-in keys.";
      }
      leaf invitations {
        type uint32;
        config false;
        description
          "Its invitations not yet used.";
      }
      leaf has-password {
        type boolean;
        config false;
        description
          "Whether it has a password of the console's (never read).";
      }
      leaf from-directory {
        type boolean;
        config false;
        description
          "Made at their directory (LDAP) sign-in, its roles those of
           their groups, brought up to date at each.";
      }
      action invite {
        description
          "A one-time token with which the user registers a first key,
           said here alone.";
        output {
          leaf token {
            type string;
            description
              "The invitation.";
          }
          leaf expires {
            type yang:date-and-time;
            description
              "When it runs out.";
          }
        }
      }
    }
  }

  container roles {
    description
      "What may be done: on the console (owner: everything; operator:
       the fleet's tools too; member: the hosts alone) and on each
       host.";
    list role {
      key "name";
      description
        "A role.";
      leaf name {
        type name;
        description
          "Its name.";
      }
      leaf console {
        type enumeration {
          enum owner;
          enum operator;
          enum member;
        }
        default "member";
        description
          "What it allows on the console.";
      }
      list host {
        key "id";
        description
          "What it allows on a host, or on all.";
        leaf id {
          type string {
            pattern '\*|[0-9a-f]{8}';
          }
          description
            "The host's id, or * for every host.";
        }
        leaf role {
          type enumeration {
            enum viewer {
              description
                "Reads.";
            }
            enum operator {
              description
                "Changes.";
            }
            enum admin {
              description
                "Also updates, moves and removes.";
            }
          }
          mandatory true;
          description
            "What it may there.";
        }
      }
      leaf ldap-group {
        type string;
        description
          "A directory group's DN whose members have the role.";
      }
      leaf created {
        type yang:date-and-time;
        config false;
        description
          "When it was made.";
      }
      leaf users {
        type uint32;
        config false;
        description
          "How many users have it.";
      }
      leaf groups {
        type uint32;
        config false;
        description
          "How many groups give it.";
      }
    }
  }

  container groups {
    description
      "Users given roles together.  Who is in a group is the user's
       group.";
    list group {
      key "name";
      description
        "A group.";
      leaf name {
        type name;
        description
          "Its name.";
      }
      leaf-list role {
        type leafref {
          path "/arcc:roles/arcc:role/arcc:name";
        }
        min-elements 1;
        description
          "The roles it gives.";
      }
      leaf description {
        type string {
          length "0..200";
        }
        description
          "What it is.";
      }
      leaf-list member {
        type string;
        config false;
        description
          "The users in it.";
      }
    }
  }

  /* Enrolment */

  container enrolment {
    config false;
    description
      "Hosts joining by a one-time token: arcana-enrol(8) on the host
       sends it with its certificate request, which the console's CA
       signs.";
    leaf enabled {
      type boolean;
      description
        "Whether the console has a CA key to sign with.";
    }
    action create-token {
      description
        "A one-time token for a host to join with, said here alone,
         and the command to run there.";
      input {
        leaf name {
          type string {
            length "1..64";
          }
          mandatory true;
          description
            "The host's name in the console.";
        }
        leaf host {
          type inet:host;
          mandatory true;
          description
            "The host's name or address, its certificate's.";
        }
        leaf port {
          type inet:port-number;
          default "4310";
          description
            "Its agent's port.";
        }
      }
      output {
        leaf token {
          type string;
          description
            "The token.";
        }
        leaf expires {
          type yang:date-and-time;
          description
            "When it runs out.";
        }
        leaf command {
          type string;
          description
            "What to run on the host.";
        }
      }
    }
  }

  /* Workflows */

  grouping test {
    description
      "A test of what is at a path.";
    leaf path {
      type string {
        length "0..256";
      }
      description
        "Words with dots, a number an array's place,
         key[field=value] the element whose field is value.";
    }
    leaf op {
      type enumeration {
        enum eq;
        enum ne;
        enum contains;
        enum gt;
        enum lt;
        enum exists;
        enum missing;
      }
      mandatory true;
      description
        "The test.";
    }
    leaf value {
      type string;
      description
        "What it is tested against.";
    }
  }

  typedef read {
    type enumeration {
      enum hello;
      enum jails;
      enum services;
      enum stats;
      enum events;
      enum history;
      enum packages;
    }
    description
      "A read of the host.";
  }

  container workflows {
    description
      "Chains of steps the console keeps and runs on several hosts at
       once, by hand, at an interval or on events.  A value in a step
       may be ${param.NAME}, ${host.id}, ${host.name}, ${step.ID.PATH}
       or ${event.PATH}.";
    list workflow {
      key "id";
      description
        "A workflow.";
      leaf id {
        type string {
          pattern '[0-9a-f]{8}';
        }
        description
          "Its id.";
      }
      leaf name {
        type string {
          length "1..64";
        }
        mandatory true;
        description
          "Its name.";
      }
      leaf-list host {
        type host-id;
        ordered-by user;
        max-elements 32;
        description
          "The hosts it runs on by itself, and by hand unless told
           others.";
      }
      leaf serial {
        type boolean;
        default "false";
        description
          "Its hosts one after the other, a failure leaving the rest
           not run; else at once.";
      }
      list param {
        key "name";
        ordered-by user;
        max-elements 16;
        description
          "A parameter, asked for when it runs.";
        leaf name {
          type string {
            length "1..32";
            pattern '[A-Za-z0-9_-]+';
          }
          description
            "Its name.";
        }
        leaf default {
          type string {
            length "0..256";
          }
          description
            "Its value unless one is given.";
        }
      }
      list step {
        key "id";
        ordered-by user;
        min-elements 1;
        max-elements 64;
        description
          "A step.";
        leaf id {
          type string {
            length "1..16";
            pattern '[A-Za-z0-9_-]+';
          }
          description
            "Its id.";
        }
        leaf name {
          type string;
          description
            "Its name; its id unless said.";
        }
        choice does {
          mandatory true;
          description
            "What it does.";
          container job {
            description
              "A job of share/arcana/jobs.yaml's kinds, checked
               against what its kind needs and uses.";
            leaf kind {
              type string;
              mandatory true;
              description
                "The job's kind.";
            }
            list field {
              key "name";
              ordered-by user;
              description
                "A field of the job.";
              leaf name {
                type string;
                description
                  "Its name.";
              }
              choice value {
                mandatory true;
                description
                  "Its value.";
                leaf text {
                  type string;
                  description
                    "Text.";
                }
                leaf number {
                  type int64;
                  description
                    "A number.";
                }
                leaf flag {
                  type boolean;
                  description
                    "True or false.";
                }
                leaf json {
                  type string;
                  description
                    "A list or a map, as RFC 8259's JSON.";
                }
              }
            }
          }
          leaf read {
            type read;
            description
              "A read of the host whose answer a later step looks
               at.";
          }
          container notify {
            description
              "A message sent.";
            leaf via {
              type notify-via;
              mandatory true;
              description
                "How.";
            }
            leaf text {
              type string {
                length "1..2000";
              }
              mandatory true;
              description
                "What it says.";
            }
          }
          container approval {
            description
              "The host's run waits here until someone approves the
               step, or stops the run, or its time runs out.";
            leaf text {
              type string {
                length "1..2000";
              }
              mandatory true;
              description
                "What is asked.";
            }
            leaf via {
              type notify-via;
              description
                "How it is told; not told unless said.";
            }
            leaf timeout {
              type uint32 {
                range "0..604800";
              }
              units "seconds";
              description
                "How long it waits; 0, as long as it takes.";
            }
          }
          leaf arcana {
            type enumeration {
              enum check;
              enum build;
              enum agents;
              enum console;
            }
            description
              "What it does to Arcana itself.";
          }
        }
        container when {
          presence "a condition";
          description
            "Its condition: a read made then, or an earlier step's
             answer, tested; a step whose condition fails is
             skipped.";
          choice of {
            mandatory true;
            description
              "What is tested.";
            leaf read {
              type read;
              description
                "A read made then.";
            }
            leaf step {
              type string;
              description
                "An earlier step's answer.";
            }
          }
          uses test;
        }
        leaf on-fail {
          type string;
          default "stop";
          description
            "On a failure: stop, continue, or a later step's id.";
        }
        leaf destroys {
          type boolean;
          config false;
          description
            "Its job destroys, as jobs.yaml says.";
        }
      }
      leaf every {
        type uint32 {
          range "0 | 60..604800";
        }
        units "seconds";
        default "0";
        description
          "It runs by itself at this interval; 0, not.";
      }
      list on {
        key "index";
        max-elements 8;
        description
          "An event it runs on: the console's (host-down, host-up) or
           a host's.  Two may be of one kind, each matching other
           values.";
        leaf index {
          type uint8 {
            range "0..7";
          }
          description
            "Its place among them, from 0, as kept.";
        }
        leaf event {
          type string {
            length "1..32";
            pattern '[A-Za-z0-9_-]+';
          }
          mandatory true;
          description
            "The event's kind.";
        }
        list match {
          key "name";
          description
            "What the event must have.";
          leaf name {
            type string;
            description
              "A member of the event.";
          }
          choice is {
            mandatory true;
            description
              "Its value; ${param.NAME}, that parameter's default.";
            leaf value {
              type string;
              description
                "Text.";
            }
            leaf number {
              type int64;
              description
                "A number.";
            }
            leaf flag {
              type boolean;
              description
                "True or false.";
            }
            leaf json {
              type string;
              description
                "A list or a map, as RFC 8259's JSON.";
            }
          }
        }
      }
      leaf destructive {
        type boolean;
        default "false";
        description
          "Said of one that runs by itself with a step that
           destroys.";
      }
      leaf changed {
        type yang:date-and-time;
        config false;
        description
          "When it was last changed.";
      }
      action run {
        description
          "It runs now, by hand.";
        input {
          leaf-list host {
            type host-id;
            description
              "Its hosts this time; its own unless said.";
          }
          list param {
            key "name";
            description
              "A parameter's value this time.";
            leaf name {
              type string;
              description
                "The parameter.";
            }
            leaf value {
              type string;
              description
                "Its value.";
            }
          }
        }
        output {
          leaf run {
            type uint32;
            description
              "The run's id.";
          }
        }
      }
    }
  }

  container runs {
    config false;
    description
      "The last runs of the workflows.  A run's traces, its steps'
       answers, are read where the path names the run.";
    list run {
      key "id";
      description
        "A run.";
      leaf id {
        type uint32;
        description
          "Its id.";
      }
      leaf workflow {
        type string;
        description
          "The workflow's id.";
      }
      leaf name {
        type string;
        description
          "The workflow's name then.";
      }
      leaf trigger {
        type string;
        description
          "What began it: hand, every, or an event.";
      }
      leaf started-by {
        type string;
        description
          "The user who ran it by hand.";
      }
      leaf state {
        type string;
        description
          "running, done, failed, cancelled or interrupted.";
      }
      leaf started {
        type yang:date-and-time;
        description
          "When it began.";
      }
      leaf ended {
        type yang:date-and-time;
        description
          "When it ended.";
      }
      list param {
        key "name";
        description
          "A parameter's value.";
        leaf name {
          type string;
          description
            "The parameter.";
        }
        leaf value {
          type string;
          description
            "Its value.";
        }
      }
      leaf event {
        type string;
        description
          "The event that began it, as RFC 8259's JSON.";
      }
      leaf cancel {
        type boolean;
        description
          "A stop was asked.";
      }
      list approved {
        key "step";
        description
          "A step approved.";
        leaf step {
          type string;
          description
            "The step.";
        }
        leaf by {
          type string;
          description
            "Who approved it.";
        }
        leaf at {
          type yang:date-and-time;
          description
            "When.";
        }
      }
      list host {
        key "id";
        description
          "A host it runs on.";
        leaf id {
          type string;
          description
            "The host's id.";
        }
        leaf name {
          type string;
          description
            "Its name.";
        }
        leaf state {
          type string;
          description
            "Its run's state.";
        }
        list step {
          key "id";
          description
            "A step there.";
          leaf id {
            type string;
            description
              "The step.";
          }
          leaf state {
            type string;
            description
              "pending, skipped, running, waiting, done, failed,
               cancelled or not run.";
          }
          leaf job {
            type uint64;
            description
              "The job it queued on the host.";
          }
          leaf title {
            type string;
            description
              "What it did.";
          }
          leaf error {
            type string;
            description
              "Why it failed.";
          }
          leaf started {
            type yang:date-and-time;
            description
              "When it began.";
          }
          leaf ended {
            type yang:date-and-time;
            description
              "When it ended.";
          }
          leaf trace {
            type string;
            description
              "What it answered, as RFC 8259's JSON.";
          }
          leaf detail {
            type string;
            description
              "What the console says of it, beside its error (one
               the console stopped during).";
          }
        }
      }
      action approve {
        description
          "A step that waits approved, on each of the run's hosts.";
        input {
          leaf step {
            type string;
            mandatory true;
            description
              "The step.";
          }
        }
      }
      action stop {
        description
          "The run stopped.";
      }
    }
    action clear {
      description
        "The runs that ended forgotten, with their traces.";
      input {
        leaf workflow {
          type string;
          description
            "Those of this workflow alone.";
        }
      }
      output {
        leaf cleared {
          type uint32;
          description
            "How many.";
        }
      }
    }
  }

  /* The fleet's tools: templates, labels, prefix lists, threat feeds,
     transfers */

  container templates {
    description
      "Configuration templates: a host's setup kept under a name, for
       other hosts to be made the same (templates.json).  A file's text
       has {{name}} where each host has a value of its own; a host's
       config is given one with its values.  A template carries no
       secret: a key is a host's own.";
    list template {
      key "name";
      description
        "A template.";
      leaf name {
        type string {
          length "1..64";
          pattern '[A-Za-z0-9_][A-Za-z0-9._-]*';
        }
        description
          "Its name.";
      }
      leaf description {
        type string {
          length "0..512";
        }
        description
          "What it is.";
      }
      leaf from {
        type string;
        description
          "The host it was made from.";
      }
      list file {
        key "path";
        ordered-by user;
        description
          "A file it writes, 1 to 512 of them.";
        leaf path {
          type string {
            length "1..255";
          }
          description
            "Where, absolute, with no '..'.";
        }
        leaf mode {
          type string {
            pattern '[0-7]{3,4}';
          }
          mandatory true;
          description
            "Its mode, in octal.";
        }
        leaf owner {
          type string;
          mandatory true;
          description
            "Its owner.";
        }
        leaf group {
          type string;
          mandatory true;
          description
            "Its group.";
        }
        leaf text {
          type string;
          mandatory true;
          description
            "Its text, 1 MB at most, {{name}} for a host's value.";
        }
      }
      list package {
        key "name";
        ordered-by user;
        description
          "A package put there by hand, as config-export says it.";
        leaf name {
          type string;
          description
            "Its name.";
        }
        leaf origin {
          type string;
          description
            "Its port's origin.";
        }
        leaf version {
          type string;
          description
            "Its version when the template was made.";
        }
      }
      leaf facts {
        type string;
        description
          "The hardware it needs, config-export's facts, as RFC 8259's
           JSON.";
      }
      list variable {
        key "name";
        description
          "A placeholder said.";
        leaf name {
          type string {
            pattern '[A-Za-z_][A-Za-z0-9_]{0,31}';
          }
          description
            "As in {{name}}.";
        }
        leaf description {
          type string;
          description
            "What it is.";
        }
        leaf default {
          type string;
          description
            "Its value when a host is given none.";
        }
      }
      leaf-list placeholder {
        type string;
        config false;
        description
          "The placeholders its files have.";
      }
      leaf updated {
        type yang:date-and-time;
        config false;
        description
          "When it was last kept.";
      }
    }
  }

  container labels {
    description
      "Labels on interfaces: a tag of the console's own for an
       interface of a host, kept here, not on the host, so that it
       names the link whatever the interface's description says
       (labels.json).  Set by whom may change the host.";
    list label {
      key "host interface";
      description
        "A label.";
      leaf host {
        type string {
          pattern '[0-9a-f]{1,16}';
        }
        description
          "The host's id.";
      }
      leaf interface {
        type string {
          length "1..15";
        }
        description
          "The interface's name.";
      }
      leaf text {
        type string {
          length "1..64";
        }
        mandatory true;
        description
          "The label, no control characters.";
      }
    }
  }

  container prefix-lists {
    description
      "Named lists of IPv4 and IPv6 prefixes, kept once and used on any
       host: an ipfw table filled from one, a BIRD set, an SD-WAN
       zone's or list's prefixes (prefix-lists.json).  Read by every
       user, changed by operators and owners.";
    list prefix-list {
      key "name";
      description
        "A list.";
      leaf name {
        type string {
          length "1..32";
          pattern '[A-Za-z0-9_-]+';
        }
        description
          "Its name.";
      }
      leaf description {
        type string {
          length "0..200";
        }
        description
          "What it is, no control characters.";
      }
      leaf-list prefix {
        type inet:ip-prefix;
        ordered-by user;
        description
          "A prefix with no host bits, 8192 at most.";
      }
    }
  }

  typedef feed-format {
    type enumeration {
      enum plain {
        description
          "An address or prefix a line, # and ; comments.";
      }
      enum spamhaus-json {
        description
          "Spamhaus DROP's JSON lines.";
      }
      enum dshield {
        description
          "DShield's block list.";
      }
    }
    description
      "How a feed's text is read.";
  }

  grouping feed-host {
    description
      "What a host was sent of a feed, or a preview's dry run there.";
    leaf host {
      type string;
      description
        "The host's id.";
    }
    leaf name {
      type string;
      description
        "Its name.";
    }
    leaf table {
      type string;
      description
        "The ipfw table.";
    }
    leaf at {
      type yang:date-and-time;
      description
        "When it took the entries.";
    }
    leaf tried-at {
      type yang:date-and-time;
      description
        "When it was last sent them.";
    }
    leaf count {
      type uint32;
      description
        "The table's entries.";
    }
    leaf added {
      type uint32;
      description
        "Those added.";
    }
    leaf removed {
      type uint32;
      description
        "Those removed.";
    }
    leaf set {
      type uint32;
      description
        "The table's set.";
    }
    leaf left-out {
      type uint32;
      description
        "Entries the host left out.";
    }
    leaf error {
      type string;
      description
        "Why it was not sent.";
    }
  }

  grouping feed-dropped {
    description
      "The entries dropped, as the reader may see them: one that covers
       an address no feed may cut off is listed only when it is a
       host's the reader may read; any other only counted.";
    list dropped {
      key "index";
      description
        "An entry dropped, the first 500.";
      leaf index {
        type uint32;
        description
          "Its place.";
      }
      leaf entry {
        type string;
        description
          "The entry, or the line that was none.";
      }
      leaf reason {
        type string;
        description
          "Why.";
      }
      leaf detail {
        type string;
        description
          "Which address it covers, and whose.";
      }
    }
    leaf protected-hidden {
      type uint32;
      description
        "Entries dropped that cover an address the reader may not be
         told of.";
    }
  }

  container threat-feeds {
    description
      "Threat feeds: lists of abusers' prefixes the console fetches
       from the internet, once for the fleet, and keeps on the hosts
       chosen as ipfw(8) tables (feeds.json, feeds-state.json).  A feed
       is fetched only from an address of the internet, checked when
       its URL is set and at each fetch and redirect.  Operators and
       owners; a feed from a URL of one's own is made, changed and
       previewed by an owner alone, an operator enabling, disabling
       or choosing its hosts.  A change of a feed needs the hosts it
       is on, and was sent to, the user's to change.  A host the
       reader may not read is only counted.";
    leaf floor {
      type uint16;
      units "hours";
      config false;
      description
        "The least interval.";
    }
    leaf max-entries {
      type uint32;
      config false;
      description
        "The most entries a feed may have.";
    }
    list preset {
      key "id";
      config false;
      description
        "A source offered, off until a feed of it is made.";
      leaf id {
        type string;
        description
          "Its id, the feed's.";
      }
      leaf name {
        type string;
        description
          "Its name.";
      }
      leaf url {
        type string;
        description
          "Where it is.";
      }
      leaf format {
        type feed-format;
        description
          "How it is read.";
      }
      leaf what {
        type string;
        description
          "What it lists.";
      }
      leaf terms {
        type string;
        description
          "Its terms of use.";
      }
      leaf terms-url {
        type string;
        description
          "Where they are.";
      }
      leaf interval {
        type uint16;
        units "hours";
        description
          "The interval its terms ask for at least.";
      }
      leaf bogons {
        type boolean;
        description
          "It lists private and reserved space on purpose.";
      }
    }
    list feed {
      key "id";
      description
        "A feed, 32 at most.";
      leaf id {
        type string {
          pattern '[a-z0-9-]{1,24}';
        }
        description
          "Its id; a preset's for one of it.";
      }
      leaf name {
        type string {
          length "1..80";
        }
        description
          "Its name; left out, its preset's or its id.";
      }
      leaf url {
        type string {
          length "1..500";
        }
        description
          "Where it is fetched, https or http; left out, its preset's.";
      }
      leaf format {
        type feed-format;
        description
          "How it is read; left out, its preset's or plain.";
      }
      leaf interval {
        type uint16 {
          range "1..720";
        }
        units "hours";
        description
          "How often it is fetched; left out, its preset's or 6.";
      }
      leaf enabled {
        type boolean;
        default "false";
        description
          "Fetched and kept on its hosts.";
      }
      leaf table {
        type string {
          length "1..48";
        }
        description
          "The ipfw table it fills; left out, feed_ and its id.";
      }
      leaf bogons {
        type boolean;
        description
          "It lists private and reserved space on purpose: kept.";
      }
      leaf preset {
        type string;
        description
          "The preset it is of.";
      }
      leaf-list host {
        type string;
        description
          "The hosts it is kept on, each the user's to change.";
      }
      leaf hosts-hidden {
        type uint32;
        config false;
        description
          "Its hosts the reader may not read.";
      }
      leaf fetched-at {
        type yang:date-and-time;
        config false;
        description
          "When it was last fetched.";
      }
      leaf tried-at {
        type yang:date-and-time;
        config false;
        description
          "When it was last tried.";
      }
      leaf changed-at {
        type yang:date-and-time;
        config false;
        description
          "When its entries last changed.";
      }
      leaf count {
        type uint32;
        config false;
        description
          "Its entries.";
      }
      leaf dropped-count {
        type uint32;
        config false;
        description
          "The entries dropped.";
      }
      leaf covered {
        type uint32;
        config false;
        description
          "The entries another covers, left out.";
      }
      leaf failures {
        type uint32;
        config false;
        description
          "Fetches failed in a row.";
      }
      leaf error {
        type string;
        config false;
        description
          "Why the last fetch failed.";
      }
      container alarm {
        config false;
        presence "An alarm is raised.";
        description
          "Raised after three failures in a row, cleared when it is
           fetched again.";
        leaf since {
          type yang:date-and-time;
          description
            "Since when.";
        }
        leaf text {
          type string;
          description
            "Why.";
        }
      }
      list delivered {
        key "host";
        config false;
        description
          "What each host it was sent to has.";
        uses feed-host;
      }
      leaf delivered-hidden {
        type uint32;
        config false;
        description
          "Hosts it was sent to that the reader may not read.";
      }
      container last-fetch {
        config false;
        description
          "What the last fetch dropped.";
        uses feed-dropped;
      }
      list event {
        key "index";
        config false;
        description
          "Its entries changed, the last 30.";
        leaf index {
          type uint32;
          description
            "Its place.";
        }
        leaf at {
          type yang:date-and-time;
          description
            "When.";
        }
        leaf count {
          type uint32;
          description
            "The entries then.";
        }
        leaf was {
          type uint32;
          description
            "The entries before.";
        }
      }
      container last-preview {
        config false;
        presence "A preview was asked.";
        description
          "The last preview: fetched whole, each host's dry run, nothing
           kept.";
        leaf at {
          type yang:date-and-time;
          description
            "When.";
        }
        leaf error {
          type string;
          description
            "Why it failed.";
        }
        leaf count {
          type uint32;
          description
            "The entries it would have.";
        }
        leaf dropped-count {
          type uint32;
          description
            "The entries it would drop.";
        }
        leaf covered {
          type uint32;
          description
            "The entries another covers.";
        }
        uses feed-dropped;
        list host {
          key "host";
          description
            "A host's dry run.";
          uses feed-host;
        }
        leaf hosts-hidden {
          type uint32;
          description
            "Hosts the reader may not read.";
        }
      }
      leaf-list sample {
        type string;
        config false;
        description
          "Its first 200 entries.";
      }
      action fetch {
        description
          "Fetched now, and sent to its hosts that lack it.";
      }
      action preview {
        description
          "Fetched whole and each host's dry run asked; nothing kept.
           A feed from a URL of one's own, an owner's alone.";
      }
    }
  }

  container transfers {
    config false;
    description
      "Snapshots sent from one host to another, the console carrying
       the bytes (transfers.json, the last 32).";
    list transfer {
      key "id";
      description
        "A transfer.";
      leaf id {
        type uint32;
        description
          "Its id.";
      }
      leaf from {
        type string;
        description
          "The sending host's id.";
      }
      leaf snapshot {
        type string;
        description
          "The snapshot sent.";
      }
      leaf since {
        type string;
        description
          "The snapshot it is sent from, incrementally.";
      }
      leaf recursive {
        type boolean;
        description
          "Its descendants' too.";
      }
      leaf to {
        type string;
        description
          "The receiving host's id.";
      }
      leaf dataset {
        type string;
        description
          "The dataset it is received as.";
      }
      leaf state {
        type enumeration {
          enum running;
          enum done;
          enum failed;
          enum cancelled;
          enum interrupted;
        }
        description
          "Where it is; interrupted, cut by the console's restart.";
      }
      leaf bytes {
        type uint64;
        description
          "The bytes carried.";
      }
      leaf error {
        type string;
        description
          "Why it failed.";
      }
      leaf started {
        type yang:date-and-time;
        description
          "When it began.";
      }
      leaf ended {
        type yang:date-and-time;
        description
          "When it ended.";
      }
      leaf cancel {
        type boolean;
        description
          "A stop was asked.";
      }
      action stop {
        description
          "A transfer that runs stopped.";
      }
    }
    action start {
      description
        "A snapshot sent; both hosts the user's to change.";
      input {
        leaf from {
          type string;
          mandatory true;
          description
            "The sending host's id.";
        }
        leaf snapshot {
          type string;
          mandatory true;
          description
            "dataset@name.";
        }
        leaf since {
          type string;
          description
            "dataset@name, for an incremental stream.";
        }
        leaf recursive {
          type boolean;
          default "false";
          description
            "Its descendants' too.";
        }
        leaf to {
          type string;
          mandatory true;
          description
            "The receiving host's id.";
        }
        leaf dataset {
          type string;
          mandatory true;
          description
            "A dataset under a pool to receive it as.";
        }
      }
      output {
        leaf id {
          type uint32;
          description
            "Its id.";
        }
      }
    }
  }

  /* Web Push */

  container push {
    description
      "The devices told by Web Push of what ends in another (push.json),
       each user's own: a user reads and changes only the subscriptions
       made in their name.  A subscription's keys are written alone,
       never read: left out of a change, they stay.";
    leaf public-key {
      type string;
      config false;
      description
        "The console's VAPID key, base64url, for a browser to
         subscribe with.";
    }
    list subscription {
      key "endpoint";
      description
        "A device, 16 at most of all users'.";
      leaf endpoint {
        type string {
          length "1..1024";
        }
        description
          "Its push service's address, https://host/path.";
      }
      leaf name {
        type string {
          length "0..80";
        }
        description
          "What the device is.";
      }
      leaf p256dh {
        type string;
        description
          "Its P-256 public key, base64url: write-only.";
      }
      leaf auth {
        type string;
        description
          "Its 16-byte secret, base64url: write-only.";
      }
      leaf service {
        type string;
        config false;
        description
          "The push service's host.";
      }
      leaf added {
        type yang:date-and-time;
        config false;
        description
          "When it was made.";
      }
    }
    action send {
      description
        "A message to the user's devices but the one at except.";
      input {
        leaf title {
          type string;
          description
            "Its title, 120 at most; left out, Arcana.";
        }
        leaf body {
          type string;
          description
            "Its text, 600 at most.";
        }
        leaf except {
          type string;
          description
            "The endpoint of the device that sends it.";
        }
      }
      output {
        leaf sent {
          type uint32;
          description
            "Taken by their push service.";
        }
        leaf gone {
          type uint32;
          description
            "Devices gone, forgotten.";
        }
        leaf failed {
          type uint32;
          description
            "Not taken.";
        }
        list result {
          key "index";
          description
            "What each push service said.";
          leaf index {
            type uint32;
            description
              "Its place.";
          }
          leaf service {
            type string;
            description
              "The push service.";
          }
          leaf status {
            type int32;
            description
              "Its HTTP status; -1, no answer.";
          }
          leaf said {
            type string;
            description
              "What it said, when it refused.";
          }
        }
      }
    }
  }

  /* The hosts */

  container hosts {
    description
      "The hosts the console manages (servers.json): each its agent's
       address, the certificate name expected of it, the tenant fleet
       it is in.  Each user reads the hosts they have a role on; a
       host is added by an operator or an owner, changed and removed
       by its admins.  What the console answers of a host itself is
       below its entry: what it holds or asks of the host, read at
       its own path alone (not in the entry's), and the console's
       verbs on it as actions.  The documents the console makes
       (drift, a bundle, a capture) are anydata, their members /api's
       (openapi.yaml); an action's input names are /api's with - for
       _.";
    leaf local {
      type enumeration {
        enum off;
        enum added;
        enum removed;
        enum absent;
        enum denied;
      }
      config false;
      description
        "The agent beside the console: not looked for, added by
         itself, taken off the list by somebody, not running, or not
         reachable by the console.";
    }
    leaf local-agent {
      type string;
      config false;
      description
        "The local agent's socket, as web.conf names it.";
    }
    list host {
      key "id";
      description
        "A host, 64 at most.";
      leaf id {
        type host-id;
        description
          "Its id, arcana-fleet's.";
      }
      leaf name {
        type string {
          length "1..64";
        }
        mandatory true;
        description
          "What it is called.";
      }
      leaf uri {
        type string {
          length "1..255";
          pattern '(tcp|sctp)://.+:[0-9]+|unix:/.+';
        }
        mandatory true;
        description
          "Where its agent is reached: tcp://host:port,
           sctp://host:port, or unix:/path.  Changed, the console
           alone reaches it there from now on (move asks the agent).";
      }
      leaf peer-name {
        type string {
          length "1..64";
          pattern '[^ ]+';
        }
        description
          "The name its certificate has, where it is not the URI's
           host.";
      }
      leaf tenant {
        type name;
        description
          "The tenant fleet it is in.";
      }
      leaf safe-wait {
        type uint32 {
          range "0 | 10..3600";
        }
        units "seconds";
        description
          "How long a change made in safe mode waits to be confirmed
           before the agent undoes it; 0 or none, the agent's own.";
      }
      list pkg-repos {
        key "jail";
        description
          "The pkg repositories each action takes packages from, per
           jail; none named, any.";
        leaf jail {
          type string {
            length "1..64";
          }
          description
            "A jail's name, . for the host.";
        }
        leaf upgrade {
          type string {
            length "0..64";
          }
          description
            "The repository upgrades come from.";
        }
        leaf install {
          type string {
            length "0..64";
          }
          description
            "The repository installs come from.";
        }
        leaf base {
          type string {
            length "0..64";
          }
          description
            "The repository the base system comes from.";
        }
      }
      leaf local {
        type boolean;
        config false;
        description
          "Reached by its local socket: the host the console runs on.";
      }
      leaf notification-token-set {
        type boolean;
        config false;
        description
          "Whether its notification receiver token is made; the token
           itself is the output of subscription-token alone.";
      }
      leaf role {
        type enumeration {
          enum viewer;
          enum operator;
          enum admin;
        }
        config false;
        description
          "The reader's role on the host; left out for an API token.";
      }
      anydata drift {
        config false;
        description
          "What the host has otherwise than its running configuration
           says, the agent asked.";
      }
      anydata watch {
        config false;
        description
          "The console's connection for the host's subscriptions, each
           topic subscribed.";
      }
      anydata notifications {
        config false;
        description
          "The notification records the host sent the console's
           receiver (RFC 8650), the newest; the query parameter after
           gives those after a record's number.";
      }
      anydata subscription {
        config false;
        description
          "What to configure on the host for it to send the console
           its notifications (ietf-subscribed-notif-receivers), but
           the token.";
      }
      anydata tls {
        config false;
        description
          "The host's own certificate, its chain and the CAs it
           trusts.";
      }
      anydata transport {
        config false;
        description
          "The agent's listeners and the connections open to it.";
      }
      anydata configuration {
        config false;
        description
          "The host as a bundle (config-export), its secrets not in
           it.";
      }
      leaf-list notify-mute {
        type enumeration {
          enum utilization {
            description
              "A limit crossed (threshold) and the cpu, memory and
               storage faults.";
          }
          enum sessions {
            description
              "Its adjacencies, tunnels and links going down and up:
               the ospf-neighbor, bgp-neighbor, bfd, tunnel,
               interface and tca faults.";
          }
          enum all {
            description
              "All of it, but what no setting stops: a commit or a
               job that could not be undone.";
          }
        }
        description
          "What of the host is neither mailed nor sent to Telegram;
           the alarms are kept and shown all the same.  Its
           admins'.";
      }
      leaf sampled {
        type boolean;
        config false;
        description
          "Whether its agent samples it, as it last said: one that
           does not has its utilization told to nobody.";
      }
      action move {
        description
          "The host reached at another address: the agent asked to
           listen there too, the new address tried, and only when it
           answers is the host moved and the old listener closed.  Its
           admins'.";
        input {
          leaf uri {
            type string;
            mandatory true;
            description
              "tcp:// or sctp://, an address and a port.";
          }
        }
        output {
          anydata result {
            description
              "ok, the URI it is reached at, why not, a note.";
          }
        }
      }
      action renew-tls {
        description
          "Its certificate renewed from the console's CA.";
        output {
          anydata result {
            description
              "What the agent said.";
          }
        }
      }
      action listen {
        description
          "The agent's SCTP listeners started again where not up, or
           bound to other addresses too.";
        input {
          leaf retry {
            type boolean;
            description
              "Start the SCTP listeners that are not up.";
          }
          leaf sctp-also {
            type string;
            description
              "The other addresses its SCTP listeners are bound to;
               empty, none.";
          }
        }
        output {
          anydata result {
            description
              "What the agent said.";
          }
        }
      }
      action switch-transport {
        description
          "The agent reached the other way at the same address and
           port, once it answers there.";
        input {
          leaf transport {
            type enumeration {
              enum sctp;
              enum tcp;
            }
            mandatory true;
            description
              "The transport to reach it by.";
          }
        }
        output {
          anydata result {
            description
              "What the agent said.";
          }
        }
      }
      action nacm-sync {
        description
          "The console's owners made the host's NACM group admin, its
           other users taken out of it; by an owner of the console.";
        output {
          anydata result {
            description
              "What the agent said.";
          }
        }
      }
      action agent-build {
        description
          "The host builds arcana-agent from agent_source, kept as the
           one the console sends.  Its admins'.";
        input {
          leaf host-keys {
            type string;
            description
              "The SSH host keys of the repository's host the user
               confirmed.";
          }
        }
        output {
          anydata result {
            description
              "What the agent said.";
          }
        }
      }
      action agent-update {
        description
          "The console's arcana-agent sent to the host.  Its admins'.";
        input {
          leaf restart {
            type boolean;
            description
              "Its service restarted after.";
          }
        }
        output {
          anydata result {
            description
              "What the agent said.";
          }
        }
      }
      action console-update {
        description
          "The console itself built and updated by the agent of the
           host it runs on (a host reached by its local socket).";
        input {
          leaf host-keys {
            type string;
            description
              "The SSH host keys the user confirmed.";
          }
        }
        output {
          anydata result {
            description
              "What the agent said.";
          }
        }
      }
      action export-configuration {
        description
          "The host as a bundle, with its secrets when asked, for who
           may change it.";
        input {
          leaf secrets {
            type boolean;
            description
              "With the secrets.";
          }
        }
        output {
          anydata result {
            description
              "The bundle.";
          }
        }
      }
      action apply-configuration {
        description
          "A bundle made the host's configuration: given, read from
           another host (its secrets not through the client), or a
           template made the host's by its values.";
        input {
          anydata bundle {
            description
              "A bundle as config-export makes it.";
          }
          leaf from {
            type host-id;
            description
              "The host whose bundle it is.";
          }
          leaf template {
            type string;
            description
              "A template's name.";
          }
          anydata values {
            description
              "The template's values.";
          }
          leaf hostname {
            type string;
            description
              "The host name the bundle gives the host.";
          }
          leaf dry-run {
            type boolean;
            description
              "What would change, nothing changed.";
          }
          leaf anyway {
            type boolean;
            description
              "Applied though the agent warns.";
          }
        }
        output {
          anydata result {
            description
              "What the agent said.";
          }
        }
      }
      action capture {
        description
          "Packets taken with tcpdump; no source, the sources there
           are.  The query parameter jail picks a jail.";
        input {
          leaf source {
            type string {
              length "1..15";
            }
            description
              "An interface's or a tap's name.";
          }
          leaf filter {
            type string {
              length "0..128";
            }
            description
              "A pcap-filter expression, one line.";
          }
          leaf packets {
            type uint32 {
              range "1..500";
            }
            description
              "The packets taken at most.";
          }
          leaf seconds {
            type uint32 {
              range "0..60";
            }
            description
              "How long at most.";
          }
        }
        output {
          anydata result {
            description
              "The packets, or the sources.";
          }
        }
      }
      action dataset-key {
        description
          "The key of an encrypted ZFS dataset of the host's, typed:
           loaded (key), or changed (key and new-key), by
           arcana-storage's load-key and change-key.  Here and not below
           the host's entry in the fleet mount: a dataset's name has a
           /, which no path there carries.  Not a job: the keys are in
           no job, no trace and no log, and are zeroed as the call
           ends.";
        input {
          leaf dataset {
            type string {
              length "1..255";
            }
            mandatory true;
            description
              "The dataset, pool/name.";
          }
          leaf key {
            type string {
              length "0..512";
            }
            description
              "Its key now.";
          }
          leaf new-key {
            type string {
              length "0..512";
            }
            description
              "The key it is to have.";
          }
        }
        output {
          anydata result {
            description
              "What the host said.";
          }
        }
      }
      action subscription-token {
        description
          "A new receiver token made for the host, the one before
           forgotten: the subscription with it, said once.";
        output {
          anydata result {
            description
              "The subscription, with the token.";
          }
        }
      }
    }
  }

  /* The SD-WAN's verbs */

  container sdwan {
    description
      "What the console makes of the services (ietf-l3vpn-ntw, the
       console's) for the edges, and its verbs on them: the plan, the
       allocation ledger, the apply, the steering pins, the IPsec key
       rotation, the named lists, the remote end points' identities,
       the records (MEF 118.1's audit trail, MEF 138's SENs and SANs,
       the security policies' record), a service's access attached to
       a free SAP (RFC 9408 Appendix D).  Operators' and owners'.
       Each node is read at its own path, a document of the console's
       (anydata, its members /api's, openapi.yaml); a record's is
       text/csv where Accept asks for it.  A refusal is /api's: 409
       where the services make no plan, an apply runs or a warning is
       not accepted.";
    anydata document {
      description
        "The services as a MEF 70.2 document (the L3NM kept, made
         one); written whole, checked first as MEF 70.2 says, kept as
         the L3NM if made from the version kept.";
    }
    anydata plan {
      config false;
      description
        "What the edges are to be made: each edge's jobs in their
         order, the changes from what was applied, the warnings an
         apply must accept.";
    }
    anydata ledger {
      config false;
      description
        "The allocations of the plan: FIBs, addresses, route
         distinguishers, VNIs, tables, with each node's resolved VPN
         instance profile.";
    }
    anydata apply-state {
      config false;
      description
        "The last apply, whether one runs, and those before.";
    }
    anydata steering {
      config false;
      description
        "The pins sent to the edges and what the edges say they
         chose.";
    }
    anydata rekeys {
      config false;
      description
        "The key rotations of the tunnels, and whether one runs.";
    }
    anydata lists {
      description
        "The named lists the policies match on: the feeds (a URL or
         text pasted) and the interval they are fetched at, each list
         as kept (version, when fetched, its count, an error) as
         state.";
    }
    anydata identities {
      config false;
      description
        "Every remote end point's identities with their addresses.";
    }
    anydata audit {
      config false;
      description
        "The audit trail, newest first, whether its chain is intact
         and where it broke; the query parameter q keeps the events
         with it anywhere in them.";
    }
    anydata sen {
      config false;
      description
        "The security event notifications (MEF 138), newest first; q
         as audit's.";
    }
    anydata san {
      config false;
      description
        "The security administration notifications (MEF 138), newest
         first; q as audit's.";
    }
    anydata record {
      config false;
      description
        "The security policies' record of every edge, newest first;
         the query parameters swvc, policy, since and edge pick.";
    }
    action check {
      description
        "A MEF 70.2 document checked, nothing kept.";
      input {
        anydata document {
          mandatory true;
          description
            "The document.";
        }
      }
      output {
        anydata result {
          description
            "ok.";
        }
      }
    }
    action apply {
      description
        "The plan applied to the edges, each in its order, the
         warnings it lists accepted.";
      input {
        leaf fresh {
          type boolean;
          description
            "Every job made again, not the changes alone.";
        }
        leaf-list accept {
          type string;
          description
            "The warnings accepted, as the plan names them.";
        }
      }
      output {
        anydata result {
          description
            "The steps begun.";
        }
      }
    }
    action pin {
      description
        "An entry of an edge's steering pinned to one of its
         candidates (none: the pin cleared), the console's override;
         the edge refuses a candidate not the entry's.";
      input {
        leaf edge {
          type string;
          mandatory true;
          description
            "The edge.";
        }
        leaf table {
          type string;
          mandatory true;
          description
            "The policy table.";
        }
        leaf prefix {
          type string;
          mandatory true;
          description
            "The far prefix.";
        }
        leaf candidate {
          type string;
          description
            "The candidate; none, the pin cleared.";
        }
      }
      output {
        anydata result {
          description
            "ok.";
        }
      }
    }
    action rekey {
      description
        "A tunnel's IPsec keys turned now.";
      input {
        leaf tunnel {
          type string {
            length "1..150";
          }
          mandatory true;
          description
            "The tunnel's id.";
        }
      }
      output {
        anydata result {
          description
            "What was begun.";
        }
      }
    }
    action fetch-lists {
      description
        "The lists' feeds fetched now: one, or all.";
      input {
        leaf name {
          type string;
          description
            "The list; none, all.";
        }
      }
      output {
        anydata result {
          description
            "fetched.";
        }
      }
    }
    action issue-identity {
      description
        "An identity issued to a remote end point, a console user's
         or a name's: its key pair made by the console, the private
         half in the WireGuard configuration said once and kept
         nowhere, the edges applied.";
      input {
        leaf swvc {
          type string;
          mandatory true;
          description
            "The service.";
        }
        leaf end-point {
          type string;
          mandatory true;
          description
            "The remote end point.";
        }
        leaf name {
          type string {
            length "1..64";
          }
          mandatory true;
          description
            "The identity's name.";
        }
        leaf zone {
          type string;
          description
            "Its zone.";
        }
        leaf group {
          type string;
          description
            "Its group of the remote's, whose zone it takes.";
        }
        leaf user {
          type boolean;
          description
            "A console user's: the name a sign-in key's.";
        }
      }
      output {
        anydata result {
          description
            "The identity and its WireGuard configuration, once.";
        }
      }
    }
    action revoke-identity {
      description
        "An identity revoked, its peer removed by the apply that
         follows.";
      input {
        leaf swvc {
          type string;
          mandatory true;
          description
            "The service.";
        }
        leaf end-point {
          type string;
          mandatory true;
          description
            "The remote end point.";
        }
        leaf name {
          type string;
          mandatory true;
          description
            "The identity's name.";
        }
      }
      output {
        anydata result {
          description
            "revoked, applied, and why not.";
        }
      }
    }
    action attach {
      description
        "A service's access placed on a free SAP of its node's host
         (RFC 9408 Appendix D), the host the user's to change.";
      input {
        leaf vpn-id {
          type string;
          mandatory true;
          description
            "The service.";
        }
        leaf vpn-node-id {
          type string;
          mandatory true;
          description
            "Its node.";
        }
        leaf sap-id {
          type string;
          description
            "The SAP; none, the first free.";
        }
        anydata access {
          description
            "L3NM's vpn-network-access.";
        }
      }
      output {
        anydata result {
          description
            "The access attached.";
        }
      }
    }
  }

  /* The console itself */

  anydata update {
    config false;
    description
      "The newest release against this one, from update_url (checked
       at most every few hours); owners'.";
  }

  anydata update-notes {
    config false;
    description
      "What is new in agent_source's repository since the version
       running: its tags' release notes, else its commits; owners'.
       The query parameters component (console or agent), from, to
       and fresh pick, as on /api.";
  }

  anydata cluster {
    config false;
    description
      "The console's cluster: its nodes, who leads, how far each has
       come.";
  }

  container ca {
    description
      "The console's CA, which signs the hosts' and its own
       certificates, and its change: a next CA made, requested of
       another or imported, rolled out to the hosts, then finished.
       Owners'.  Neither ietf-keystore nor ietf-truststore: they keep
       keys and certificates, not a rollover across a fleet.  A key
       is written, never read.";
    anydata state {
      config false;
      description
        "The CA now, the next one, the change's state.";
    }
    action make {
      description
        "A next CA made here.";
      input {
        leaf cn {
          type string {
            length "0..64";
          }
          description
            "Its common name; none, arcana CA.";
        }
      }
      output {
        anydata result {
          description
            "The CA's state.";
        }
      }
    }
    action request {
      description
        "A key made here, its certificate signing request for another
         CA to sign.";
      input {
        leaf cn {
          type string {
            length "0..64";
          }
          description
            "Its common name.";
        }
      }
      output {
        anydata result {
          description
            "The CA's state, the request in it.";
        }
      }
    }
    action import {
      description
        "A next CA given: its certificate, and its key unless the
         request's.";
      input {
        leaf cert {
          type string;
          mandatory true;
          description
            "PEM.";
        }
        leaf key {
          type string;
          description
            "PEM: write-only.";
        }
      }
      output {
        anydata result {
          description
            "The CA's state.";
        }
      }
    }
    action discard {
      description
        "The next CA thrown away, before it is rolled out.";
      output {
        anydata result {
          description
            "The CA's state.";
        }
      }
    }
    action rollout {
      description
        "The next CA sent to every host as trusted, their certificates
         renewed by it.";
      input {
        leaf force {
          type boolean;
          description
            "Past the hosts that do not answer.";
        }
      }
      output {
        anydata result {
          description
            "The CA's state.";
        }
      }
    }
    action finish {
      description
        "The old CA no longer trusted anywhere.";
      input {
        leaf force {
          type boolean;
          description
            "Past the hosts that do not answer.";
        }
      }
      output {
        anydata result {
          description
            "The CA's state.";
        }
      }
    }
  }

  container plugins {
    description
      "The console's plugins in its plugins directory, each enabled or
       not by an owner, every user's to read; each plugin's store, a
       user's own or the one shared (written by operators and owners),
       read and written at its own path by a signed-in user alone.";
    leaf directory {
      type string;
      config false;
      description
        "Where they are installed; told to owners.";
    }
    list plugin {
      key "id";
      description
        "A plugin.";
      leaf id {
        type string {
          length "1..40";
          pattern '[a-z0-9-]+';
        }
        description
          "Its directory's name.";
      }
      leaf enabled {
        type boolean;
        default "false";
        description
          "Its files served to the page; an owner's to change.";
      }
      leaf name {
        type string;
        config false;
        description
          "Its manifest's name.";
      }
      leaf version {
        type string;
        config false;
        description
          "Its version.";
      }
      leaf arcana {
        type string;
        config false;
        description
          "The console versions it is for.";
      }
      leaf description {
        type string;
        config false;
        description
          "What it does.";
      }
      leaf author {
        type string;
        config false;
        description
          "Who made it.";
      }
      leaf-list provides {
        type string;
        config false;
        description
          "What it gives the page.";
      }
      leaf error {
        type string;
        config false;
        description
          "Why it cannot be enabled.";
      }
      list file {
        key "path";
        config false;
        description
          "A file it lists.";
        leaf path {
          type string;
          description
            "Its path in the plugin.";
        }
        leaf kind {
          type enumeration {
            enum script;
            enum style;
            enum asset;
          }
          description
            "What the page does with it.";
        }
        leaf size {
          type uint64;
          units "bytes";
          description
            "Its size.";
        }
        leaf integrity {
          type string;
          description
            "Its subresource integrity, sha384-.";
        }
      }
      anydata store {
        description
          "The reader's own store of the plugin, a JSON object; written
           whole, with If-Match its entity-tag where one is kept.";
      }
      anydata shared-store {
        description
          "The store every user of the plugin shares; written by
           operators and owners.";
      }
    }
  }

  container credentials {
    description
      "The security keys users sign in with (WebAuthn): each user
       their own, an owner every user's.  Registered by the WebAuthn
       ceremony beside RESTCONF; here renamed and removed, never the
       last; their public keys are not read.";
    list credential {
      key "id";
      description
        "A key.";
      leaf id {
        type string;
        description
          "Its credential id, base64url.";
      }
      leaf name {
        type string {
          length "1..64";
        }
        description
          "What its user calls it.";
      }
      leaf user {
        type string;
        config false;
        description
          "Whose it is.";
      }
      leaf alg {
        type int32;
        config false;
        description
          "Its COSE algorithm.";
      }
      leaf created {
        type yang:date-and-time;
        config false;
        description
          "When it was registered.";
      }
      leaf last-used {
        type yang:date-and-time;
        config false;
        description
          "When it last signed in.";
      }
      leaf sign-count {
        type uint32;
        config false;
        description
          "Its signature counter.";
      }
      leaf-list transports {
        type string;
        config false;
        description
          "How the browser reaches it.";
      }
    }
  }

  rpc trace-path {
    description
      "The path finder: a packet's way from src to dst through the
       hosts asked, each one's routes and rules; it changes nothing.
       Operators' and owners'.";
    input {
      leaf src {
        type inet:ip-address-no-zone;
        mandatory true;
        description
          "Its source.";
      }
      leaf dst {
        type inet:ip-address-no-zone;
        mandatory true;
        description
          "Its destination, of the source's family.";
      }
      leaf proto {
        type enumeration {
          enum tcp;
          enum udp;
          enum sctp;
          enum icmp;
          enum ip;
        }
        description
          "Its protocol.";
      }
      leaf port {
        type inet:port-number;
        description
          "Its destination port.";
      }
      list places {
        description
          "The hosts asked, a jail of one where named; none, every
           host.";
        leaf server {
          type host-id;
          description
            "The host.";
        }
        leaf jail {
          type string;
          description
            "A jail of it.";
        }
      }
    }
    output {
      anydata result {
        description
          "The path, hop by hop.";
      }
    }
  }

  rpc wireguard-keypair {
    description
      "A fresh WireGuard key pair and a preshared key for a client of
       a host's wg interface, said once and kept nowhere.  Operators'
       and owners'.";
    output {
      anydata result {
        description
          "The private and public halves, base64, and the preshared
           key.";
      }
    }
  }
}
