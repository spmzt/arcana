module arcana-netgraph {
  yang-version 1.1;
  namespace "urn:arcana:yang:arcana-netgraph";
  prefix arcng;

  import cblink-gen {
    prefix cg;
  }

  organization
    "Arcana";
  contact
    "Pouria Mousavizadeh Tehrani <pouria@FreeBSD.org>";
  description
    "FreeBSD's netgraph(4) graph on a host, or in a vnet jail of it,
     as ngctl(8) list -l tells of it: each node with its name, type and
     id, and each of its hooks with the node and hook at the other end.
     The graph is changed by jobs of kind netgraph (mkpeer, connect,
     rmhook, shutdown, ngctl's own words).  A vnet jail's graph is the
     read action's, given the jail.  The netgraph kind
     of the network operation of arcana.yaml converted and retired
     (Y-3).";

  revision 2026-10-15 {
    description
      "Initial revision.";
  }

  grouping nodes {
    description
      "The nodes of a graph.";
    list node {
      cg:struct "node";
      key "id";
      description
        "A node.";
      leaf id {
        type string;
        description
          "Its id, hexadecimal, as ngctl prints it.";
      }
      leaf name {
        type string;
        description
          "Its name, when it has one.";
      }
      leaf type {
        type string;
        description
          "Its type: ether, bridge, eiface, socket ...";
      }
      list hook {
        key "name";
        description
          "Its hooks, each connected to a hook of another node.";
        leaf name {
          type string;
          description
            "The hook's name.";
        }
        leaf peer {
          type string;
          description
            "The node at the other end, by name.";
        }
        leaf peer-type {
          type string;
          description
            "Its type.";
        }
        leaf peer-id {
          type string;
          description
            "Its id.";
        }
        leaf peer-hook {
          type string;
          description
            "Its hook.";
        }
      }
    }
  }

  container netgraph {
    config false;
    description
      "netgraph(4), where it runs.";
    uses nodes;
    action read {
      description
        "The graph as ngctl lists it now, the host's or a vnet jail's,
         what it said where it could not.";
      input {
        leaf jail {
          type string;
          description
            "A running vnet jail's, which a read of the jails leaves
             out; none, the host's.";
        }
      }
      output {
        uses nodes;
      }
    }
  }
}
